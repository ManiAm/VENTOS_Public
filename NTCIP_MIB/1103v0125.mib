-- A.1. TMP MIB Header
-- Filename: 1103v0125.mib
-- Description:     This MIB defines various objects related to managing and 
-- monitoring the Transportation Management Protocols.  Specifically, these
-- include objects related to: 
--		(a) configuration of dynamic objects, 
-- 		(b) communication statistics, 
-- 		(c) configuration of community names,
--		(d) managing event information that can be logged in the device, and
--		(e) the mapping of logical names to network addresses
-- This MIB replaces TMIB-II.
--
-- MIB Revision History:
-- 08/01/96     Original standard approved
-- 01/01/98     Preliminary Release of TS 3.2 TMIB MIB formatted for 80
--                    columns and no TABs
-- 01/07/98     Replaced some missed TABs with spaces
-- 07/08/98     Added Copyright Notice
-- 10/07/98     Amendment 1
-- 03/09/00     Removed all the special edits to that were done to use the 
--                    SMIC Compiler
--                    Defined DisplayString to eliminate reference to RFC 1212
--                    END is still left "Dynamic Object Data" group
--                    Changed filename and updated copyright years
--                    Updated the MIB to Amendment 1
-- 08/09/00     Modified header format and wording of copyright and MIB
-- 11/16/01     Added objects for sfmp and stmp statistics
--                    Moved security node into this MIB from NTCIP 1201
--                    Added objects to support logical names
--                    Renamed the module to NTCIP1103-A-2002 from TMIB-II
--                    Renamed the text name to Transportation Management
--                    Protocols MIB from Transportation MIB
--                    Changed STATUS of all objects to optional to reflect new 
--                    conformance rules being defined in NTCIP 8004
-- 06/08/04     Moved report node into this MIB from NTCIP 1201
-- 09/27/04     Changed name of file.
-- 10/11/04     Per KLV e-mails 10/08/04 updated version and 
--              Changed Index on logicalNameTranslation-index from (0..255) to (1..255)
--              Changed all STATUS optional to mandatory
--
--              DISTRIBUTION NOTICE
--Copyright 1996 - 2004 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--Except for the MIB, Do not copy without written permission of either AASHTO,
--ITE, or NEMA.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************

NTCIP1103-A-2004 DEFINITIONS ::= BEGIN

IMPORTS
        Gauge, Counter, NetworkAddress, Opaque, null
            FROM RFC1155-SMI
	OBJECT-TYPE
		FROM RFC-1212
	DisplayString
		FROM RFC1213-MIB
	OwnerString, RowStatusStatic, dynObjMgmt, profiles, application, global, OerString
		FROM NTCIP8004-A-2004;
-- EXPORTS EVERYTHING

-- A.2. Type Definitions
ConfigEntryStatus  ::= INTEGER
     { valid (1),
       underCreation (2),
       invalid (3)
     }
-- See Clause 5.2.4.1 of NTCIP 1103 for the complete definition of this Type.

-- A.3. Objects for SNMP 
snmpConfig OBJECT IDENTIFIER ::= {application 1}

-- A.3.1. Maximum SNMP Packet Size Parameter
snmp-maxPacketSize OBJECT-TYPE
     SYNTAX    INTEGER (484..65535)
     ACCESS    read-only
     STATUS    mandatory
     DESCRIPTION
          "Indicates the maximum packet size, in octets, that the SNMP agent
           supports for reception or transmission."
     ::= {snmpConfig 1}

-- A.4. Objects for SFMP
sfmp OBJECT IDENTIFIER ::= {application 2}

sfmpStatistics OBJECT IDENTIFIER ::= { sfmp 1 }

-- A.4.1. Number of Incoming SFMP Packets
sfmp-inPkts   OBJECT-TYPE
     SYNTAX   Counter
     ACCESS   read-only
     STATUS   mandatory
     DESCRIPTION
          "The total number of Messages delivered to the SFMP entity for 
          processing ."
::= { sfmpStatistics 1 }

-- A.4.2. Number of Outgoing SFMP Packets
sfmp-outPkts   OBJECT-TYPE
     SYNTAX   Counter
     ACCESS   read-only
     STATUS   mandatory
     DESCRIPTION
          "The total number of SFMP PDU's which were generated by the SFMP
          protocol entity ."
::= { sfmpStatistics 2 }

-- A.4.3. Number of Incoming SFMP Packets with Bad Version Numbers
sfmp-inBadVersions OBJECT-TYPE
     SYNTAX  Counter
     ACCESS  read-only
     STATUS  mandatory
     DESCRIPTION
          "The total number of SFMP Messages which were delivered to the SFMP 
          protocol entity and were for an unsupported SFMP version."
     ::= { sfmpStatistics 3 }

-- A.4.4. Number of Incoming SFMP Packets with Bad Community Names
sfmp-inBadCommunityNames OBJECT-TYPE
     SYNTAX  Counter
     ACCESS  read-only
     STATUS  mandatory
     DESCRIPTION
          "The total number of SFMP Messages delivered to the SFMP protocol 
          entity which used a SFMP community name not known to said entity."
     ::= { sfmpStatistics 4 }

-- A.4.5. Number of Incoming SFMP Packets with Bad Use of a Community Name
sfmp-inBadCommunityUses OBJECT-TYPE
     SYNTAX  Counter
     ACCESS  read-only
     STATUS  mandatory
     DESCRIPTION
          "The total number of SFMP Messages delivered to the SFMP protocol
          entity which represented an SFMP operation which was not allowed by 
          the SFMP community named in the Message."
     ::= { sfmpStatistics 5 }

-- A.4.6. Number of Incoming SFMP Packets with Parsing Errors
sfmp-inParseErrs   OBJECT-TYPE
     SYNTAX  Counter
     ACCESS  read-only
     STATUS  mandatory
     DESCRIPTION 
          "The total number of OER errors encountered by the SFMP protocol 
          entity when decoding received SFMP Messages."
     ::= { sfmpStatistics 6 }

-- A.4.7. Reserved
-- node 7 is reserved for bad types in order to parallel SNMP, but it does not 
-- apply to SFMP

-- A.4.8. Number of Incoming SFMP Packets indicating a Too Big Error
sfmp-inTooBigs   OBJECT-TYPE
     SYNTAX  Counter
     ACCESS  read-only
     STATUS  mandatory
     DESCRIPTION
          "The total number of SFMP PDUs which were delivered to the SFMP 
          protocol entity with a Message Type of Error and Error Number of 
          tooBig."
     ::= { sfmpStatistics 8 }

-- A.4.9. Number of Incoming SFMP Packets indicating a No Such Name Error
sfmp-inNoSuchNames   OBJECT-TYPE
     SYNTAX  Counter
     ACCESS  read-only
     STATUS  mandatory
     DESCRIPTION 
          "The total number of SFMP PDUs which were delivered to the SFMP 
          protocol entity with a Message Type of Error and Error Number of 
          noSuchName."
     ::= { sfmpStatistics 9 }

-- A.4.10. Number of Incoming SFMP Packets indicating a Bad Value Error
sfmp-inBadValues   OBJECT-TYPE
     SYNTAX  Counter
     ACCESS  read-only
     STATUS  mandatory
     DESCRIPTION 
          "The total number of SFMP PDUs which were delivered to the SFMP
          protocol entity with a Message Type of Error and Error Number of
          badValue."
     ::= { sfmpStatistics 10 }

-- A.4.11. Number of Incoming SFMP Packets indicating a Read-Only Error
sfmp-inReadOnlys   OBJECT-TYPE
     SYNTAX  Counter
     ACCESS  read-only
     STATUS  mandatory
     DESCRIPTION 
          "The total number of SFMP PDUs which were delivered to the SFMP 
          protocol entity with a Message Type of Error and Error Number of
          readOnly."
     ::= { sfmpStatistics 11 }

-- A.4.12. Number of Incoming SFMP Packets indicating a General Error
sfmp-inGenErrs   OBJECT-TYPE
     SYNTAX  Counter
     ACCESS  read-only
     STATUS  mandatory
     DESCRIPTION 
          "The total number of SFMP PDUs which were delivered to the SFMP
          protocol entity with a Message Type of Error and Error Number of 
          genError."
     ::= { sfmpStatistics 12 }

-- A.4.13. Reserved
-- node 13 is reserved for total request vars in order to parallel SNMP, but it
-- does not apply to SFMP

-- A.4.14. Reserved
-- node 14 is reserved for total set vars in order to parallel SNMP, but it does
-- not apply to SFMP

-- A.4.15. Number of Incoming SFMP Get Requests
sfmp-inGetRequests   OBJECT-TYPE
     SYNTAX  Counter
     ACCESS  read-only
     STATUS  mandatory
     DESCRIPTION  
          "The total number of SFMP Get-Request PDUs which have been accepted 
          and processed by the SFMP protocol entity."
     ::= { sfmpStatistics 15 }

-- A.4.16. Reserved
-- node 16 is reserved for in get nexts in order to parallel SNMP, but it does
-- not apply to SFMP

-- A.4.17. Number of Incoming SFMP Set Requests
sfmp-inSetRequests   OBJECT-TYPE
     SYNTAX  Counter
     ACCESS  read-only
     STATUS  mandatory
     DESCRIPTION  
          "The total number of SFMP Set-Request PDUs which have been accepted 
          and processed by the SFMP protocol entity."
     ::= { sfmpStatistics 17 }

-- A.4.18. Number of Incoming SFMP Get Responses
sfmp-inGetResponses   OBJECT-TYPE
     SYNTAX  Counter
     ACCESS  read-only
     STATUS  mandatory
     DESCRIPTION 
         "The total number of SFMP Get-Response PDUs which have been accepted 
         and processed by the SFMP protocol entity."
     ::= { sfmpStatistics 18 }

-- A.4.19. Reserved
-- node 19 is reserved for traps to parallel SNMP, but it 
-- does not apply to SFMP at present

-- A.4.20. Number of Outgoing SFMP Packets indicating a Too Big Error
sfmp-outTooBigs   OBJECT-TYPE
     SYNTAX  Counter
     ACCESS  read-only
     STATUS  mandatory
     DESCRIPTION 
          "The total number of SFMP PDUs which were generated by the SFMP 
          protocol entity with a Message Type of Error and Error Number of 
          tooBig."
     ::= { sfmpStatistics 20 }

-- A.4.21. Number of Outgoing SFMP Packets indicating a No Such Name Error
sfmp-outNoSuchNames   OBJECT-TYPE
     SYNTAX  Counter
     ACCESS  read-only
     STATUS  mandatory
     DESCRIPTION 
          "The total number of SFMP PDUs which were generated by the SFMP
          protocol entity with a Message Type of Error and Error Number of
          noSuchname."
     ::= { sfmpStatistics 21 }

-- A.4.22. Number of Outgoing SFMP Packets indicating a Bad Value Error
sfmp-outBadValues   OBJECT-TYPE
     SYNTAX  Counter
     ACCESS  read-only
     STATUS  mandatory
     DESCRIPTION 
          "The total number of SFMP PDUs which were generated by the SFMP 
          protocol entity with a Message Type of Error and Error Number of
          badValue."
     ::= { sfmpStatistics 22 }

-- A.4.23. Number of Outgoing SFMP Packets indicating a Read-Only Error
sfmp-outReadOnly   OBJECT-TYPE
     SYNTAX  Counter
     ACCESS  read-only
     STATUS  mandatory
     DESCRIPTION 
          "The total number of SFMP PDUs which were generated by the SFMP
          protocol entity with a Message Type of Error and Error Number of 
          readOnly."
     ::= { sfmpStatistics 23 }

-- A.4.24. Number of Outgoing SFMP Packets indicating a General Error
sfmp-outGenError   OBJECT-TYPE
     SYNTAX  Counter
     ACCESS  read-only
     STATUS  mandatory
     DESCRIPTION
          "The total number of SFMP PDUs which were generated by the SFMP 
          protocol entity with a Message Type of Error and Error Number of 
          genErr."
     ::= { sfmpStatistics 24 }

-- A.4.25. Number of Outgoing SFMP Get Requests
sfmp-outGetRequests   OBJECT-TYPE
     SYNTAX  Counter
     ACCESS  read-only
     STATUS  mandatory
     DESCRIPTION
          "The total number of SFMP PDU's with a Message Type of Get-Request, 
          which have been generated by the SFMP protocol entity."
     ::= { sfmpStatistics 25 }

-- A.4.26. Reserved
-- node 26 is reserved for out get nexts in order to parallel SNMP, but it does 
-- not apply to SFMP

-- A.4.27. Number of Outgoing SFMP Set Requests
sfmp-outSetRequests   OBJECT-TYPE
     SYNTAX  Counter
     ACCESS  read-only
     STATUS  mandatory
     DESCRIPTION
          "The total number of SFMP PDU's with a Message Type of Set-Request,
          which have been generated by the SFMP protocol entity."
     ::= { sfmpStatistics 27 }

-- A.4.28. Number of Outgoing SFMP Get Responses
sfmp-outGetResponses   OBJECT-TYPE
     SYNTAX  Counter
     ACCESS  read-only
     STATUS  mandatory
     DESCRIPTION
          "The total number of SFMP PDU's with a Message Type of Get-Response,
          which have been generated by the SFMP protocol entity."
     ::= { sfmpStatistics 28 }

-- A.4.29. Reserved
-- node 29 is reserved for traps to parallel SNMP, but it
-- does not apply to SFMP at present 

-- A.4.30. Reserved
-- node 30 is reserved for enable authentication traps to parallel SNMP, but it
-- does not apply to SFMP 

-- A.4.31. Number of Incoming SFMP Set Requests – No Replies
sfmp-inSetRequestsNoReply   OBJECT-TYPE
     SYNTAX  Counter
     ACCESS  read-only
     STATUS  mandatory
     DESCRIPTION 
          "The total number of SFMP Set-Request No Reply PDUs which have been 
          accepted and processed by the SFMP protocol entity."
     ::= { sfmpStatistics 31 }

-- A.4.32. Number of Incoming SFMP Set Responses
sfmp-inSetResponses   OBJECT-TYPE
     SYNTAX  Counter
     ACCESS  read-only
     STATUS  mandatory
     DESCRIPTION 
          "The total number of SFMP Set-Response PDUs which have been accepted 
          and processed by the SFMP protocol entity."
     ::= { sfmpStatistics 32 }

-- A.4.33. Number of Incoming SFMP Error Responses
sfmp-inErrorResponses   OBJECT-TYPE
     SYNTAX  Counter
     ACCESS  read-only
     STATUS  mandatory
     DESCRIPTION
          "The total number of SFMP Error-Response PDUs which have been accepted
          and processed by the SFMP protocol entity."
     ::= { sfmpStatistics 33 }

-- A.4.34. Number of Outgoing SFMP Set Requests – No Replies
sfmp-outSetRequestsNoReply   OBJECT-TYPE
     SYNTAX  Counter
     ACCESS  read-only
     STATUS  mandatory
     DESCRIPTION 
          "The total number of SFMP PDU's with a Message Type of Set-Request-No-
          Reply, which have been generated by the SFMP protocol entity."
     ::= { sfmpStatistics 34 }

-- A.4.35. Number of Outgoing SFMP Set Responses
sfmp-outSetResponses   OBJECT-TYPE
     SYNTAX  Counter
     ACCESS  read-only
     STATUS  mandatory
     DESCRIPTION 
          "The total number of SFMP PDU's with a Message Type of Set-Response, 
          which have been generated by the SFMP protocol entity."
     ::= { sfmpStatistics 35 }

-- A.4.36. Number of Outgoing SFMP Error Responses
sfmp-outErrorResponses   OBJECT-TYPE
     SYNTAX  Counter
     ACCESS  read-only
     STATUS  mandatory
     DESCRIPTION
          "The total number of SFMP PDU's with a Message Type of Error-Response,
          which have been generated by the SFMP protocol entity."
     ::= { sfmpStatistics 36 }


-- A.5. Objects for STMP
dynObjData   OBJECT IDENTIFIER ::= { dynObjMgmt 2 }
stmp         OBJECT IDENTIFIER ::= { application 3 }

-- A.5.1. Dynamic Object Definition Table
dynObjDef  OBJECT-TYPE
     SYNTAX  SEQUENCE OF DynObjEntry
     ACCESS  not-accessible
     STATUS  mandatory
     DESCRIPTION
          "A list of objects to be included in dynamic objects"
     ::= { dynObjMgmt 1 }

dynObjEntry  OBJECT-TYPE
     SYNTAX  DynObjEntry
     ACCESS  not-accessible
     STATUS  mandatory
     DESCRIPTION
          "A list of OBJECT IDENTIFIERs that make up a dynamic object"
     INDEX  { dynObjNumber,  dynObjIndex }
     ::= { dynObjDef 1 }

DynObjEntry ::= SEQUENCE {
     dynObjNumber	      INTEGER (1..13),
     dynObjIndex		INTEGER,
     dynObjVariable	OBJECT IDENTIFIER
     }
    -- dynObjOwner & dynObjStatus were deprecated from the
    -- DynObjEntry structure.  See Annex B.

-- A.5.1.1. Dynamic Object Number
dynObjNumber  OBJECT-TYPE
     SYNTAX  INTEGER ( 1..13)
     ACCESS  read-only
     STATUS  mandatory
     DESCRIPTION
          "The dynamic object number that this entry is to be associated with."
     ::= { dynObjEntry 1 }

-- A.5.1.2. Dynamic Object Index
dynObjIndex  OBJECT-TYPE
     SYNTAX  INTEGER (1..255)
     ACCESS  read-only
     STATUS  mandatory
     DESCRIPTION
          "An index that uniquely identifies an entry in the dynamic object
          table.  Each entry defines an object that is to be associated with a
          dynamic object number.  The dynObjIndex determines the order in which
          objects are transmitted for the associated dynamic object. The lower
          dynObjIndex numbers are transmitted before larger numbers for entries
          within the same dynamic object."
     ::= { dynObjEntry 2 }

-- A.5.1.3. Dynamic Object Variable
dynObjVariable OBJECT-TYPE
     SYNTAX  OBJECT IDENTIFIER
     ACCESS  read-write
     STATUS  mandatory
     DESCRIPTION
          "The complete object identifier of the particular variable to be included in
          the specified dynamic object number. Care must be taken when defining
          dynamic objects so that the maximum size of all the objects included
          in a dynamic object do not exceed the maximum packet size of the
          communications network.

          When set to reference a columnar object, an agent may wish to only
          validate the prefix portion of the object identifier.  The suffix or
          index portion of an object identifier need not be instantiated or
          exist at the time a dynObjVariable is defined.

          This object shall not reference any of the objects identified in NTCIP
          1103 Clause 8.2.

          This object may not be modified unless the associated
          dynObjConfigStatus object is equal to underCreation."
     DEFVAL  {null}
     ::= { dynObjEntry 3 }

-- A.5.1.4. Reserved
-- { dynObjEntry 4 } is a deprecated node that was a columnar object of the DynObjEntry sequence.  See Annex B.

-- A.5.1.5. Reserved
-- { dynObjEntry 5 } is a deprecated node that was a columnar object of the DynObjEntry sequence.  See Annex B.

-- A.5.2. Dynamic Object Data
-- { dynObjData 1 } is deprecated.  See Annex B.

-- { dynObjData 2 } is deprecated.  See Annex B.

-- { dynObjData 3 } is deprecated.  See Annex B.

-- { dynObjData 4 } is deprecated.  See Annex B.

-- { dynObjData 5 } is deprecated.  See Annex B.

-- { dynObjData 6 } is deprecated.  See Annex B.

-- { dynObjData 7 } is deprecated.  See Annex B.

-- { dynObjData 8 } is deprecated.  See Annex B.

-- { dynObjData 9 } is deprecated.  See Annex B.

-- { dynObjData 10 } is deprecated.  See Annex B.

-- { dynObjData 11 } is deprecated.  See Annex B.

-- { dynObjData 12 } is deprecated.  See Annex B.

-- { dynObjData 13 } is deprecated.  See Annex B.


-- A.5.3. Dynamic Object Configuration
dynObjConfigTable  OBJECT-TYPE
     SYNTAX  SEQUENCE OF DynObjConfigEntry
     ACCESS  not-accessible
     STATUS  mandatory
     DESCRIPTION
          "A table consisting of an owner and status for each of the 13 dynamic 
          object definitions."
     ::= { dynObjMgmt 3}

dynObjConfigEntry  OBJECT-TYPE
     SYNTAX  DynObjConfigEntry
     ACCESS  not-accessible
     STATUS  mandatory
     DESCRIPTION
          "A table consisting of an owner and status for each of the 13 dynamic
          object definitions."
     INDEX  {dynObjNumber}
     ::= {dynObjConfigTable  1}

DynObjConfigEntry ::= SEQUENCE {
     dynObjConfigOwner     OwnerString,
     dynObjConfigStatus     ConfigEntryStatus}

-- A.5.3.1. Dynamic Object Configuration Owner
dynObjConfigOwner OBJECT-TYPE
     SYNTAX  OwnerString
     ACCESS  read-write
     STATUS  mandatory
     DESCRIPTION
          "The entity that configured the associated dynamic object.   This 
          object may not be modified unless the associated dynObjConfigStatus 
          object is equal to underCreation."
     DEFVAL     {""}
     ::= {dynObjConfigEntry 1}

-- A.5.3.2. Dynamic Object Configuration Status
dynObjConfigStatus OBJECT-TYPE
     SYNTAX  ConfigEntryStatus
     ACCESS  read-write
     STATUS  mandatory
     DESCRIPTION
          "Indicates the state of the associated dynamic object.  Depending on 
          the validity checks that are performed on the dynamic object
          definition, a set request may or may not be honored.   See Clause
          5.2.4.1 for a complete description."
     ::= {dynObjConfigEntry 2}

-- A.5.4. STMP Statistics
stmpStatistics OBJECT IDENTIFIER ::= { stmp 1 }

-- A.5.4.1. Number of Incoming STMP Packets
stmp-inPkts   OBJECT-TYPE
     SYNTAX   Counter
     ACCESS   read-only
     STATUS   mandatory
     DESCRIPTION 
          "The total number of Messages delivered to the STMP entity for 
          processing."
     ::= { stmpStatistics 1 }

-- A.5.4.2. Number of Outgoing STMP Packets
stmp-outPkts   OBJECT-TYPE
     SYNTAX   Counter
     ACCESS   read-only
     STATUS   mandatory
     DESCRIPTION
          "The total number of STMP PDU's which were generated by the STMP 
          protocol entity ."
     ::= { stmpStatistics 2 }

-- A.5.4.3. Reserved
-- node 3 is reserved for bad version in order to parallel SNMP, but it does not 
-- apply to STMP 

-- A.5.4.4. Reserved
-- node 4 is reserved for bad community name in order to parallel SNMP, but it 
-- does not apply to STMP

-- A.5.4.5. Reserved
-- node 5 is reserved for bad community use in order to parallel SNMP, but it 
-- does not apply to STMP

-- A.5.4.6. Number of Incoming STMP Packets with Parsing Errors
stmp-inParseErrs   OBJECT-TYPE
     SYNTAX  Counter
     ACCESS  read-only
     STATUS  mandatory
     DESCRIPTION 
          "The total number of OER errors encountered by the STMP protocol 
          entity when decoding received STMP Messages."
     ::= { stmpStatistics 6 }

-- A.5.4.7. Reserved
-- node 7 is reserved for bad types in order to parallel SNMP, but it does not
-- apply to STMP

-- A.5.4.8. Number of Incoming STMP Packets indicating a Too Big Error
stmp-inTooBigs   OBJECT-TYPE
     SYNTAX  Counter
     ACCESS  read-only
     STATUS  mandatory
     DESCRIPTION 
          "The total number of STMP PDUs which were delivered to the STMP 
          protocol entity with a Message Type of Error and Error Number of 
          tooBig."
     ::= { stmpStatistics 8 }

-- A.5.4.9. Number of Incoming STMP Packets indicating a No Such Name Error
stmp-inNoSuchNames   OBJECT-TYPE
     SYNTAX  Counter
     ACCESS  read-only
     STATUS  mandatory
     DESCRIPTION
          "The total number of STMP PDUs which were delivered to the STMP
          protocol entity with a Message Type of Error and Error Number of
          noSuchName."
     ::= { stmpStatistics 9 }

-- A.5.4.10. Number of Incoming STMP Packets indicating a Bad Value Error
stmp-inBadValues   OBJECT-TYPE
     SYNTAX  Counter
     ACCESS  read-only
     STATUS  mandatory
     DESCRIPTION
          "The total number of STMP PDUs which were delivered to the STMP 
          protocol entity with a Message Type of Error and Error Number of 
          badValue."
     ::= { stmpStatistics 10 }

-- A.5.4.11. Number of Incoming STMP Packets indicating a Read-Only Error
stmp-inReadOnlys   OBJECT-TYPE
     SYNTAX  Counter
     ACCESS  read-only
     STATUS  mandatory
     DESCRIPTION 
          "The total number of STMP PDUs which were delivered to the STMP 
          protocol entity with a Message Type of Error and Error Number of 
          readOnly."
     ::= { stmpStatistics 11 }

-- A.5.4.12. Number of Incoming STMP Packets indicating a General Error
stmp-inGenErrs   OBJECT-TYPE
     SYNTAX  Counter
     ACCESS  read-only
     STATUS  mandatory
     DESCRIPTION 
          "The total number of STMP PDUs which were delivered to the STMP 
          protocol entity with a Message Type of Error and Error Number of 
          genError."
     ::= { stmpStatistics 12 }

-- A.5.4.13. Reserved
-- node 13 is reserved for total request vars in order to parallel SNMP, but it 
-- does not apply to STMP

-- A.5.4.14. Reserved
-- node 14 is reserved for total set vars in order to parallel SNMP, but it does
-- not apply to STMP

-- A.5.4.15. Number of Incoming STMP Get Requests
stmp-inGetRequests   OBJECT-TYPE
     SYNTAX  Counter
     ACCESS  read-only
     STATUS  mandatory
     DESCRIPTION  
          "The total number of STMP Get-Request PDUs which have been accepted 
          and processed by the STMP protocol entity."
     ::= { stmpStatistics 15 }

-- A.5.4.16. Number of Incoming STMP Get Next Requests
stmp-inGetNexts   OBJECT-TYPE
     SYNTAX  Counter
     ACCESS  read-only
     STATUS  mandatory
     DESCRIPTION
          "The total number of STMP Get-Next PDUs which have been accepted and 
          processed by the STMP protocol entity."
     ::= { stmpStatistics 16 }

-- A.5.4.17. Number of Incoming STMP Set Requests
stmp-inSetRequests   OBJECT-TYPE
     SYNTAX  Counter
     ACCESS  read-only
     STATUS  mandatory
     DESCRIPTION  
          "The total number of STMP Set-Request PDUs which have been accepted 
          and processed by the STMP protocol entity."
     ::= { stmpStatistics 17 }

-- A.5.4.18. Number of Incoming STMP Get Responses
stmp-inGetResponses   OBJECT-TYPE
     SYNTAX  Counter
     ACCESS  read-only
     STATUS  mandatory
     DESCRIPTION
          "The total number of STMP Get-Response PDUs which have been accepted 
          and processed by the STMP protocol entity."
     ::= { stmpStatistics 18 }

-- A.5.4.19. Reserved
-- node 19 is reserved for in trap responses in order to parallel SNMP, but it 
-- does not apply to STMP

-- A.5.4.20. Number of Outgoing STMP Packets indicating a Too Big Error
stmp-outTooBigs   OBJECT-TYPE
     SYNTAX  Counter
     ACCESS  read-only
     STATUS  mandatory
     DESCRIPTION 
          "The total number of STMP PDUs which were generated by the STMP 
          protocol entity with a Message Type of Error and Error Number of 
          tooBig."
     ::= { stmpStatistics 20 }

-- A.5.4.21. Number of Outgoing STMP Packets indicating a No Such Name Error 
stmp-outNoSuchNames   OBJECT-TYPE
     SYNTAX  Counter
     ACCESS  read-only
     STATUS  mandatory
     DESCRIPTION
          "The total number of STMP PDUs which were generated by the STMP 
          protocol entity with a Message Type of Error and Error Number of 
          noSuchname."
     ::= { stmpStatistics 21 }

-- A.5.4.22. Number of Outgoing STMP Packets indicating a Bad Value Error
stmp-outBadValues   OBJECT-TYPE
     SYNTAX  Counter
     ACCESS  read-only
     STATUS  mandatory
     DESCRIPTION 
          "The total number of STMP PDUs which were generated by the STMP 
          protocol entity with a Message Type of Error and Error Number of
          badValue."
     ::= { stmpStatistics 22 }

-- A.5.4.23. Number of Outgoing STMP Packets indicating a Read-Only Error
stmp-outReadOnly   OBJECT-TYPE
     SYNTAX  Counter
     ACCESS  read-only
     STATUS  mandatory
     DESCRIPTION 
          "The total number of STMP PDUs which were generated by the STMP 
          protocol entity with a Message Type of Error and Error Number of
          readOnly."
     ::= { stmpStatistics 23 }

-- A.5.4.24. Number of Outgoing STMP Packets indicating a General Error
stmp-outGenError   OBJECT-TYPE
     SYNTAX  Counter
     ACCESS  read-only
     STATUS  mandatory
     DESCRIPTION 
          "The total number of STMP PDUs which were generated by the STMP 
          protocol entity with a Message Type of Error and Error Number of 
          genErr."
     ::= { stmpStatistics 24 }

-- A.5.4.25. Number of Outgoing STMP Get Requests
stmp-outGetRequests   OBJECT-TYPE
     SYNTAX  Counter
     ACCESS  read-only
     STATUS  mandatory
     DESCRIPTION
          "The total number of STMP PDU's with a Message Type of Get-Request,
          which have been generated by the STMP protocol entity."
     ::= { stmpStatistics 25 }

-- A.5.4.26. Number of Outgoing STMP Get Next Requests
stmp-outGetNexts   OBJECT-TYPE
     SYNTAX  Counter
     ACCESS  read-only
     STATUS  mandatory
     DESCRIPTION
          "The total number of STMP PDU's with a Message Type of Get-Next, which 
          have been generated by the STMP protocol entity."
     ::= { stmpStatistics 26 }

-- A.5.4.27. Number of Outgoing STMP Set Requests
stmp-outSetRequests   OBJECT-TYPE
     SYNTAX  Counter
     ACCESS  read-only
     STATUS  mandatory
     DESCRIPTION 
          "The total number of STMP PDU's with a Message Type of Set-Request, 
          which have been generated by the STMP protocol entity."
     ::= { stmpStatistics 27 }

-- A.5.4.28. Number of Outgoing STMP Get Responses
stmp-outGetResponses   OBJECT-TYPE
     SYNTAX  Counter
     ACCESS  read-only
     STATUS  mandatory
     DESCRIPTION
          "The total number of STMP PDU's with a Message Type of Get-Response,
          which have been generated by the STMP protocol entity."
     ::= { stmpStatistics 28 }

-- A.5.4.29. Reserved
-- node 29 is reserved for in trap responses in order to parallel SNMP, but it 
-- does not apply to STMP

-- A.5.4.30. Reserved
-- node 30 is reserved for enable authentication traps to parallel SNMP, but it
-- does not apply to STMP 

-- A.5.4.31. Number of Incoming STMP Set Request – No Replies
stmp-inSetRequestsNoReply   OBJECT-TYPE
     SYNTAX  Counter
     ACCESS  read-only
     STATUS  mandatory
     DESCRIPTION 
          "The total number of STMP Set-Request No Reply PDUs which have been
          accepted and processed by the STMP protocol entity."
     ::= { stmpStatistics 31 }

-- A.5.4.32. Number of Incoming STMP Set Responses
stmp-inSetResponses   OBJECT-TYPE
     SYNTAX  Counter
     ACCESS  read-only
     STATUS  mandatory
     DESCRIPTION 
          "The total number of STMP Set-Response PDUs which have been accepted
          and processed by the STMP protocol entity."
     ::= { stmpStatistics 32 }

-- A.5.4.33. Number of Incoming STMP Error Responses
stmp-inErrorResponses   OBJECT-TYPE
     SYNTAX  Counter
     ACCESS  read-only
     STATUS  mandatory
     DESCRIPTION 
          "The total number of STMP Error-Response PDUs which have been accepted 
          and processed by the STMP protocol entity."
     ::= { stmpStatistics 33 }

-- A.5.4.34. Number of Outgoing STMP Set Request – No Replies
stmp-outSetRequestsNoReply   OBJECT-TYPE
     SYNTAX  Counter
     ACCESS  read-only
     STATUS  mandatory
     DESCRIPTION 
          "The total number of STMP PDU's with a Message Type of Set-Request-No-
          Reply, which have been generated by the STMP protocol entity."
     ::= { stmpStatistics 34 }

-- A.5.4.35. Number of Outgoing STMP Set Responses
stmp-outSetResponses   OBJECT-TYPE
     SYNTAX  Counter
     ACCESS  read-only
     STATUS  mandatory
     DESCRIPTION 
          "The total number of STMP PDU's with a Message Type of Set-Response,
          which have been generated by the STMP protocol entity."
     ::= { stmpStatistics 35 }

-- A.5.4.36. Number of Outgoing STMP Error Responses
stmp-outErrorResponses   OBJECT-TYPE
     SYNTAX  Counter
     ACCESS  read-only
     STATUS  mandatory
     DESCRIPTION 
          "The total number of STMP PDU's with a Message Type of Error-Response, 
          which have been generated by the STMP protocol entity."
     ::= { stmpStatistics 36 }


-- A.5.5. STMP Configuration
profilesSTMP OBJECT IDENTIFIER ::= { profiles 2 }

-- This node is an identifier used to group all objects for support of 
-- configuration functions that are common to device types that support the STMP 
-- protocol.  The objects under this node are placed under the 
-- Protocols\Profiles\STMP subtree within the NEMA node.  

-- A.5.5.1. Dynamic Object Persistence
dynamicObjectPersistence  OBJECT-TYPE
     SYNTAX     INTEGER (0..65535)
     ACCESS     read-write
     STATUS     mandatory
     DESCRIPTION
          "The maximum power outage time in minutes that may occur before all 
          STMP dynamic object definitions in a device shall be invalidated.  If
          this object is set to zero then existing dynamic object definintions
          shall be invalidated on device power up.  If this object is set to its
          maximum value (65535) the existing dynamic object definitions shall 
          nominally persist for an infinite period (in practice this will be limited 
          by the non-volatile memory capabilities of the device) 
          This object shall not be invalidated due to power outages of any 
          duration.  A device that supports STMP dynamic objects 
          shall support this object."
     DEFVAL {65535}
     ::= { profilesSTMP 1 }

-- A.5.5.2. Dynamic Object Configuration ID
dynamicObjectTable-ConfigID  OBJECT-TYPE
     SYNTAX     INTEGER (0..65535)
     ACCESS     read-only
     STATUS     mandatory
     DESCRIPTION
          "Specifies a relatively unique ID (e.g., this could be a counter, a 
          check-sum, etc.) for the current values stored in the 
          dynObjVariable and dynObjConfigOwner objects for 
          all dynamic objects with a dynObjStatus of valid.  This 
          value shall be calculated on the change of any dynObjStatus 
          to or from the valid state. This value reported by this object shall 
          not change unless there has been a change in the data since the 
          last request; however a genErr shall be returned if the unique ID
          value has not yet been updated.  A management station will be able
          to detect any change in the configuration of dynamic objects by monitoring 
          this value after it has established a baseline. "
     ::= { profilesSTMP 2 }




-- A.6. Logical Names
logicalNames OBJECT IDENTIFIER ::= { application 4 }
-- This node is used to define objects to allow a mapping between logical device 
-- names and network addresses.

-- A.6.1. Maximum Logical Name Translations
logicalNameTranslationTable-maxEntries     OBJECT-TYPE
     SYNTAX    INTEGER (1..255)
     ACCESS    read-only
     STATUS    mandatory
     DESCRIPTION
          "This object specifies the maximum number of rows that may be
          implemented in the logical name translation table."
     ::= { logicalNames 1 }

-- A.6.2. Logical Name Translation Table
logicalNameTranslationTable  OBJECT-TYPE
     SYNTAX    SEQUENCE OF LogicalNameTranslationEntry
     ACCESS    not-accessible
     STATUS    mandatory
     DESCRIPTION
          "This table defines the logical names of the other network entities
          with which the device may communicate and maps these names to the
          network addresses of those devices."
     ::= { logicalNames 2 }

logicalNameTranslationEntry  OBJECT-TYPE
     SYNTAX    LogicalNameTranslationEntry
     ACCESS    not-accessible
     STATUS    mandatory
     DESCRIPTION
          "This is one logical row of the logical name translation table."
     INDEX     { logicalNameTranslation-index }
     ::= { logicalNameTranslationTable 1}

LogicalNameTranslationEntry::=SEQUENCE
     { logicalNameTranslation-index              INTEGER,
       logicalNameTranslation-logicalName        OCTET STRING,
       logicalNameTranslation-networkAddress     NetworkAddress,
       logicalNameTranslation-status             RowStatusStatic
     }

-- A.6.2.1. Index for the Logical Name Translation
logicalNameTranslation-index  OBJECT-TYPE
     SYNTAX  INTEGER (1..255)
     ACCESS  read-only
     STATUS  mandatory
     DESCRIPTION
          "This object provides the index into the logical name table."
     ::=  { logicalNameTranslationEntry 1 }

-- A.6.2.2. Logical Name for the Logical Name Translation
logicalNameTranslation-logicalName  OBJECT-TYPE
     SYNTAX  OCTET STRING (SIZE (0..32))
     ACCESS  read-write
     STATUS  mandatory
     DESCRIPTION
          "This object defines the logical name of the network entity for which
          this row is defined."
     DEFVAL  { "" }
     ::=  { logicalNameTranslationEntry 2 }

-- A.6.2.3. Network Address of the Logical Name Translation
logicalNameTranslation-networkAddress OBJECT-TYPE
     SYNTAX  NetworkAddress
     ACCESS  read-write
     STATUS  mandatory
     DESCRIPTION
          "This object defines the network address of the associated network
          entity for the given profile.  If the transport profile is ‘internet,’
          the network address is the IP address of the entity stored as an
          IpAddress.  If the transport profile is ‘t2,’ there is no physical
          network address, but the entity is assigned a dummy IP address in
          order to abstract the mapping to the ipNetToMediaTable
          defined in MIB-II."
--     DEFVAL { internet '00000000'h  }
     ::= { logicalNameTranslationEntry 3 }

-- A.6.2.4. Logical Name Translation Status
logicalNameTranslation-status OBJECT-TYPE
     SYNTAX  RowStatusStatic 
     ACCESS  read-write
     STATUS  mandatory
     DESCRIPTION
          "This object allows for the management of rows within the table."
     DEFVAL  { invalid }
     ::= { logicalNameTranslationEntry 4 }

-- A.7. Report Parameter Node
globalReport OBJECT IDENTIFIER
::= { global 4 }

-- This node is an identifier used to organize all objects for support of report functions
-- that are common to most device types.

-- NOTE—The event class table is presented first in order to ease the readability of the standard; however, the node numbers assigned to this table reflect the original node numbering used in the original 1996 specification in order to preserve backwards compatibility with existing systems.
-- A.7.1. Maximum Event Classes Parameter
maxEventClasses OBJECT-TYPE
SYNTAX	INTEGER (1..255)
ACCESS	read-only
STATUS	mandatory
DESCRIPTION
"<Definition> The object defines the number of rows in the eventClassTable that this device supports.  This is a static table.
<DescriptiveName>EventClassTable.maxEventClasses:quantity
<DataConceptType>Data Element
<Unit>EventClass"
::= { globalReport 5 }

-- A.7.2. Event Class Table
eventClassTable OBJECT-TYPE
SYNTAX	SEQUENCE OF EventClassEntry
ACCESS	not-accessible
STATUS	mandatory
DESCRIPTION
"<Definition>This table is used to configure event logging limits and log table maintenance. 
<DescriptiveName>EventClassTable
<DataConceptType>Entity Type
<TableType> static"
::= { globalReport 6 }

eventClassEntry  OBJECT-TYPE
SYNTAX	EventClassEntry
ACCESS	not-accessible
STATUS	mandatory
DESCRIPTION
"<Definition>This defines a row in the Event Class Table
<DescriptiveName>EventClass
<DataConceptType>Entity Type"
INDEX { eventClassNumber }
::= { eventClassTable 1 }

EventClassEntry ::= SEQUENCE {
eventClassNumber		INTEGER,
eventClassLimit  		INTEGER,
eventClassClearTime 		Counter,
eventClassDescription 		OCTET STRING,
eventClassNumRowsInLog 	INTEGER,
eventClassNumEvents		INTEGER }

-- A.7.2.1. Event Class Number Parameter
eventClassNumber OBJECT-TYPE
SYNTAX	INTEGER (1..255)
ACCESS	read-only
STATUS	mandatory
DESCRIPTION
"<Definition>This is a class value that is to be configured. 
<DescriptiveName>EventClass.number:identifier 
<DataConceptType>Data Element"
::= { eventClassEntry 1 }

-- A.7.2.2. Event Class Limit Parameter
eventClassLimit OBJECT-TYPE
SYNTAX	INTEGER (0..255)
ACCESS	read-write
STATUS	mandatory
DESCRIPTION
"<Definition>This object specifies the maximum number of events of the associated class to store in the log.  Once the limit is reached, the oldest entry of the matching class will be overwritten by any new entry of the same class.  If the value of this object is set to a number smaller than the current number of rows within this class in the eventLogTable, then the oldest entries shall be lost/deleted. The sum of all event class limits shall not exceed the maxEventLogSize object; if a SET operation to this object causes the sum of eventClassLimit objects to exceed maxEventLogSize, then the agent shall respond with a genErr.
<DescriptiveName>EventClass.eventLimit:quantity
<DataConceptType>Data Element
<Unit>Event"
::= { eventClassEntry 2 }

-- A.7.2.3. Event Class Clear Time Parameter
eventClassClearTime OBJECT-TYPE
SYNTAX	Counter
ACCESS	read-write
STATUS	mandatory
DESCRIPTION
"<Definition>This object is used to clear multiple event log entries from the eventLogTable.  All events of this class that have an eventLogTime equal to or less than this object shall be cleared from the eventLogTable.  If this object has a value greater than the current value of globalTime, it shall prevent the logging of any events of this class.
<DescriptiveName>EventClass.clearTime:quantity
<DataConceptType>Data Element
<Unit>second"
DEFVAL	{0}
::= { eventClassEntry 3 }


-- A.7.2.4. Event Class Description Parameter
eventClassDescription OBJECT-TYPE
SYNTAX	OCTET STRING
ACCESS	read-write
STATUS	mandatory
DESCRIPTION
"<Definition>This object specifies a description of the class in ASCII characters.
<DescriptiveName>EventClass.description:text
<DataConceptType>Data Element"
::= { eventClassEntry 4 }

-- A.7.2.5. Event Class Number of Rows in Event Log Table Parameter
eventClassNumRowsInLog OBJECT-TYPE
SYNTAX	INTEGER (0..255)
ACCESS	read-only
STATUS	mandatory
DESCRIPTION
"<Definition>The number of rows for this class that currently exist in the eventLogTable.
<DescriptiveName>EventClass.currentEntries:quantity
<DataConceptType>Data Element
<Unit>Event"
::= { eventClassEntry 5 }

-- A.7.2.6. Class Event Log Counter Parameter
eventClassNumEvents OBJECT-TYPE
SYNTAX	INTEGER (0..65535)
ACCESS	read-only
STATUS	mandatory
DESCRIPTION
"<Definition> This object is a counter that gets incremented every time an event occurs for this class; it shall initialize to zero at power up.  The value shall roll over each time it exceeds the maximum of 65535. 
<DescriptiveName>EventClass.eventCounter:quantity 
<DataConceptType>Data Element
<Unit>Events"
::= { eventClassEntry 6 }

-- A.7.3. Maximum Event Log Configurations Parameter
maxEventLogConfigs   OBJECT-TYPE
SYNTAX	INTEGER (1..65535)
ACCESS	read-only
STATUS	mandatory
DESCRIPTION
"<Definition>The number of rows that exist in the static eventLogConfig table for this device.
<DescriptiveName>EventTypeTable.maxEventTypes:quantity
<DataConceptType>Data Element
<Unit>EventType"
::= { globalReport 1}

-- A.7.4. Event Log Configuration Table
eventLogConfigTable   OBJECT-TYPE
SYNTAX	SEQUENCE OF EventLogConfigEntry
ACCESS	not-accessible
STATUS	mandatory
DESCRIPTION
"<Definition>A table containing Event Log Configuration information. The number of rows in this table is equal to the maxEventLogConfigs object.  This table defines the parameters that the device will monitor to create an event.
<DescriptiveName>EventTypeTable
<DataConceptType>Entity Type
<TableType> static"
::= { globalReport 2 }

eventLogConfigEntry OBJECT-TYPE
SYNTAX	EventLogConfigEntry
ACCESS	not-accessible
STATUS	mandatory
DESCRIPTION
"<Definition>This object defines an entry in the event log configuration table.
<DescriptiveName>EventType
<DataConceptType>Entity Type"
INDEX { eventConfigID }
::= { eventLogConfigTable 1 }

EventLogConfigEntry ::= SEQUENCE {
eventConfigID 		INTEGER,
eventConfigClass		INTEGER,
eventConfigMode		INTEGER,
eventConfigCompareValue	INTEGER,
eventConfigCompareValue2	INTEGER,
eventConfigCompareOID	OBJECT IDENTIFIER,
eventConfigLogOID		OBJECT IDENTIFIER,
eventConfigAction		INTEGER,
eventConfigStatus		INTEGER }

-- A.7.4.1. Event Log Configuration ID Parameter
eventConfigID  OBJECT-TYPE
SYNTAX	INTEGER (1..65535)
ACCESS	read-only
STATUS	mandatory
DESCRIPTION
"<Definition>This object contains the row number which is used to identify the event associated with this row in the eventLogConfigTable.  The number of event IDs shall not exceed the value indicated in the maxEventLogConfigs object.
<DescriptiveName>EventType.identifier:identifier
<DataConceptType>Data Element"
::= { eventLogConfigEntry 1 }

-- A.7.4.2. Event Log Configuration Class Parameter
eventConfigClass OBJECT-TYPE
SYNTAX	INTEGER (1..255)
ACCESS	read-write
STATUS	mandatory
DESCRIPTION
"<Definition>This object contains the class value to assign to the event associated with this row in the event configuration table.  This value is used in the event log table to organize various events defined in this table into logical groupings.  This value shall not exceed the maxEventClasses object value.  

 NOTE2—The event cannot be logged if the EventClass has an eventClassLimit of zero (0), 
<DescriptiveName>EventType.class:identifier
<DataConceptType>Data Element "
DEFVAL	{1}
::= { eventLogConfigEntry 2 }

-- A.7.4.3. Event Log Configuration Mode Parameter
eventConfigMode OBJECT-TYPE
SYNTAX	INTEGER { other (1),
onChange (2),
greaterThanValue (3),
smallerThanValue (4),
hysteresisBound (5),
periodic (6),
andedWithValue (7) }
ACCESS	read-write
STATUS	mandatory
DESCRIPTION
"<Definition>This object specifies the mode of operation for this event. The modes are defined as follows:
Value			Description
other	the event mode of operation is not described in this standard, refer to the device manual.
onChange 	create a log entry when the object value referenced by eventConfigCompareOID changes.  The values of eventConfigCompareValue and eventConfigCompareValue2 are ignored in this mode.
greaterThanValue 	create a log entry when the object value referenced by eventConfigCompareOID becomes greater than the value of eventConfigCompareValue for the time (tenth seconds) defined by eventConfigCompareValue2 (zero means immediate logging).
smallerThanValue 	create a log entry when the object value referenced by eventConfigCompareOID becomes less than the value of eventConfigCompareValue for the time (tenth seconds) defined by eventConfigCompareValue2 (zero means immediate logging).
hysteresisBound 	create a log entry when the object value referenced by eventConfigCompareOID becomes less than or greater than the bound values.  The lowerbound value is the lower value of eventConfigCompareValue and eventConfigCompareValue2; the upperbound value is the higher value of the two values. 
When the object value becomes greater than the upper bound value, subsequent logging of upperbound conditions shall not occur until the object value becomes less than the lower bound value.
When the object value becomes less than the lower bound value, subsequent logging of lowerbound conditions shall not occur until the object value becomes greater than the upper bound value.
periodic	create a log entry every x seconds, where x is defined by the value stored in eventConfigCompareValue.  The values stored in eventConfigCompareValue2 and eventConfigCompareOID are ignored in this mode.
andedWithValue 	create a log entry when the object value referenced by eventConfigCompareOID ANDED with the value of eventConfigCompareValue is NOT equal to zero for the time (tenth seconds) defined by eventConfigCompareValue2 (zero means immediate logging).  This allows monitoring of a specific bit; the condition becomes true anytime that any one of the selected bits become true.

<DescriptiveName>EventType.mode:code
<DataConceptType>Data Element"
DEFVAL	{onChange}
::= { eventLogConfigEntry 3 }

-- A.7.4.4. Event Log Configuration Compare Value Parameter
eventConfigCompareValue OBJECT-TYPE
SYNTAX	INTEGER
ACCESS	read-write
STATUS	mandatory
DESCRIPTION
"<Definition>This object contains the comparision value to use with eventConfigMode values (greaterThanValue, smallerThanValue, hysteresisBound ).  No value within this object is necessary when the eventConfigMode-object has the value onChange (2).
<DescriptiveName>EventType.compareValue:number
<DataConceptType>Data Element"
DEFVAL	{0}
::= { eventLogConfigEntry 4 }

-- A.7.4.5. Event Log Configuration Compare Value 2 Parameter
eventConfigCompareValue2 OBJECT-TYPE
SYNTAX	INTEGER
ACCESS	read-write
STATUS	mandatory
DESCRIPTION
"<Definition>If the eventConfigMode is set to hysteresisBound, this object specifies the second comparison value for the hysteresis.  If the eventConfigMode is set to greaterThanValue, smallerThanValue, or andedWithValue, this object specifies the time (in tenth of seconds, +1 tenth / -0 tenths) for which the samples used for comparison must be true prior to the event condition becoming true.  If the eventConfigMode is set to onChange or periodic, the value of this object shall be ignored. 

The amount of time the condition must be true is measured in tenths of a second. The accuracy of this timer is limited to +1 tenth of a second and –0 tenths of a second.  If the event is true for at least the time shown in this parameter +1 tenth of a second, the condition shall trigger a log entry.  It is recognized that some designs only sample the condition periodically, in which case the condition must be true for at least the time indicated by this object before the event becomes true and the event shall always become true if the condition is true for a duration equal to the value shown in this object plus 1 tenth of a second.
<DescriptiveName>EventType.compareValue2:number
<DataConceptType>Data Element"
DEFVAL 	{0}
::= { eventLogConfigEntry 5 }

-- A.7.4.6. Event Log Configuration Compare Object Identifier Parameter
eventConfigCompareOID OBJECT-TYPE
SYNTAX	OBJECT IDENTIFIER
ACCESS	read-write
STATUS	mandatory
DESCRIPTION
"<Definition>This object contains the object identifier which references the value against which the comparison is made.  If the eventConfigMode is set to periodic, the value of this object shall be ignored.  If the eventConfigMode is set to greaterThanValue, smallerThanValue or hysteresisBound, this object must reference an object whose SYNTAX resolves to a ranged or unranged INTEGER.  As with all other objects that are sub-ranged by a given implementation, an agent should return a badValue error if it receives a set command indicating a OID which is not supported by the implementation or which is not null.
<DescriptiveName>EventType.compareObject:identifier
<DataConceptType>Data Element"
DEFVAL	{null}
::= { eventLogConfigEntry 6 }

-- A.7.4.7. Event Log Configuration Log Object Identifier Parameter
eventConfigLogOID OBJECT-TYPE
SYNTAX	OBJECT IDENTIFIER
ACCESS	read-write
STATUS	mandatory
DESCRIPTION
"<Definition>This object contains the object identifier which indicates what value to log when a condition or event occurs (e.g., log the phase display when the watchdog alarm status changes). As with all other objects that are sub-ranged by a given implementation, an agent should return a badValue error if it receives a set command indicating a value which is not supported by the implementation.  The valid value range of this object shall not include any values, other than null, that do not correspond to objects that may exist within the agent, although it may be further restricted.

The valid value range of this object shall not include objects under the following nodes:
* Security - { nema transportation devices global security }
* CHAP - { nema transportation protocols layers chap }

<DescriptiveName>EventType.logObject:identifier
<DataConceptType>Data Element"
DEFVAL	{null}
::= { eventLogConfigEntry 7 }

-- A.7.4.8. Event Log Configuration Action Parameter
eventConfigAction  OBJECT-TYPE
SYNTAX	INTEGER { other (1),
disabled (2),
log (3)
}
ACCESS	read-write
STATUS	mandatory
DESCRIPTION
"<Definition>The value of this object indicates what action shall take place when this event occurs.  
disabled  - no entry will be recorded due to this event.
log - an entry will be recorded in the event log table when this event occurs.

<DescriptiveName>EventType.action:code
<DataConceptType>Data Element"
DEFVAL	{disabled}
::= { eventLogConfigEntry 8 }

-- A.7.4.9. Event Log Configuration Status Parameter
eventConfigStatus  OBJECT-TYPE
SYNTAX	INTEGER { other (1),
disabled (2),
log (3),
error (4)
}
ACCESS	read-only
STATUS	mandatory
DESCRIPTION
"<Definition>The value of this object indicates the current status of the configured event. Upon setting any object in this row of the eventLogConfigTable, the agent will determine if the setting is valid and will set this object to one of the following states:
other	indicates that the action is successfully set to a mode other than that defined in this standard
disabled	indicates that the action is set to disabled

log	indicates that the action is successfully set to the log state after passing consistency checks.

error	indicates that the requested action could not be implemented due to a consistency check 
<DescriptiveName>EventType.status:code
<DataConceptType>Data Element"
::= { eventLogConfigEntry 9 }

-- A.7.5. Maximum Event Log Size Parameter
maxEventLogSize   OBJECT-TYPE
SYNTAX	INTEGER (1..65535)
ACCESS	read-only
STATUS	mandatory
DESCRIPTION
"<Definition>The maximum, fixed number of rows that can be utilized within the eventLogTable. 
<DescriptiveName>EventTable.maxEventLogSize:quantity
<DataConceptType>Data Element
<Unit>Event"
::= { globalReport 3}

-- A.7.6. Event Log Table
eventLogTable   OBJECT-TYPE
SYNTAX	SEQUENCE OF EventLogEntry
ACCESS	not-accessible
STATUS	mandatory
DESCRIPTION
"<Definition>A table containing Event History data collected. A request for an object from a row that has not been instantiated or has been cleared shall return a noSuchName error.
<DescriptiveName>EventTable
<DataConceptType>Entity Type
<TableType> dynamic status"
::= { globalReport 4 }

eventLogEntry OBJECT-TYPE
SYNTAX	EventLogEntry
ACCESS	not-accessible
STATUS	mandatory
DESCRIPTION
"<Definition>This object defines an entry in the event log table
<DescriptiveName>Event
<DataConceptType>Entity Type"
INDEX { eventLogClass, eventLogNumber }
::= { eventLogTable 1 }

EventLogEntry ::= SEQUENCE {
eventLogClass		INTEGER,
eventLogNumber 	        INTEGER,
eventLogID 		INTEGER,
eventLogTime  		Counter,
eventLogValue 		Opaque }

-- A.7.6.1. Event Log Class Parameter
eventLogClass OBJECT-TYPE
SYNTAX	INTEGER (1..255)
ACCESS	read-only
STATUS	mandatory
DESCRIPTION
"<Definition>This object contains the class of the associated event as defined in the eventLogConfig Table. 
<DescriptiveName>ClassLog.class:identifier
<DataConceptType>Data Element"
::= { eventLogEntry 1 }

-- A.7.6.2. Event Log Number Parameter
eventLogNumber OBJECT-TYPE
SYNTAX	INTEGER (1..255)
ACCESS	read-only
STATUS	mandatory
DESCRIPTION
"<Definition>The event number within this class for this event.  Event numbers shall be assigned starting at 1 and shall increase to the value specified by the associated eventClassLimit for the class associated with the rows.  Events shall maintain a chronological ordering in the table with the oldest event of a class occupying the row with eventNumber = 1, and subsequent events filling subsequent rows. This ordering shall be maintained for those rows still remaining when events are cleared. 
<DescriptiveName>Event.number:identifier
<DataConceptType>Data Element"
::= { eventLogEntry 2 }

-- A.7.6.3. Event Log ID Parameter
eventLogID  OBJECT-TYPE
SYNTAX	INTEGER (1..65535)
ACCESS	read-only
STATUS	mandatory
DESCRIPTION
"<Definition>This object contains the event configuration ID (from the eventLogConfigTable) that caused this table entry.  It indicates the row in the eventLogConfig table reponsible for this event entry.
<DescriptiveName>Event.type:identifier
<DataConceptType>Data Element"
::= { eventLogEntry 3 }

-- A.7.6.4. Event Log Time Parameter
eventLogTime OBJECT-TYPE
SYNTAX	Counter
ACCESS	read-only
STATUS	mandatory
DESCRIPTION
"<Definition>The time that the event was detected.  If the device supports the globalTime object, the value shall reflect the value of globalTime when the event occurred, otherwise this shall be the time in seconds since the device powered up. The event shall be detected and timestamped within one second from the event becoming true.  The event shall be logged in the table within five seconds of the event being detected. These timing resolutions may be modified by a device profile. 
<DescriptiveName>Event.logTime:quantity
<DataConceptType>Data Element
<Unit>second"
::= { eventLogEntry 4 }

-- A.7.6.5. Event Log Value Parameter
eventLogValue  OBJECT-TYPE
SYNTAX	Opaque
ACCESS	read-only
STATUS	mandatory
DESCRIPTION
"<Definition>The value of this object is set to the BER encoding of the value referenced by the eventConfigLogOID of the associated eventLogID when the event was logged.  Its length is variable.  The value shall not contain any padding characters either before or after the values.
NOTE – Opaque objects are doubly wrapped.  For SNMP operations, which use BER, this would be {type, length, {type, length, value}}.  For example, a zero-length octet string, would be encoded in BER as 0x44 02 04 00.  For STMP or SFMP operations, which use OER, this would be { length, {type, length, value}}.  For example, the same example would be encoded in OER as 0x02 04 00.  
<DescriptiveName>Event.logValue:frame
<DataConceptType>Data Element"
::= { eventLogEntry 5 }

-- A.7.7. Total Event Log Counter Parameter
numEvents OBJECT-TYPE
SYNTAX	INTEGER (0..65535)
ACCESS	read-only
STATUS	mandatory
DESCRIPTION
"<Definition> This object is a counter that gets incremented every time an event occurs and shall initialize to zero at power up.  The value shall roll over each time it exceeds the maximum of 65535. 
<DescriptiveName>EventTable.numEvents:quantity 
<DataConceptType>Data Element
<Unit>Events"
::= { globalReport 7 }


-- A.8. Security Objects
security OBJECT IDENTIFIER ::= {global 5}
-- This node is an identifier used to group all objects related to the
-- assignment of community names and the access rights they provide.
-- These objects were previously defined in NTCIP 1201, but were moved 
-- here as they relate to the protocols more than the end application.

-- A.8.1. Community Name Administrator Parameter
communityNameAdmin OBJECT-TYPE
     SYNTAX    OCTET STRING (SIZE(8..16))
     ACCESS    read-write
     STATUS    mandatory
     DESCRIPTION
          "This object is the community name that must be used to specifically 
          gain access to information under the security node.  A message with 
          this value in the community name field of an SNMP message has user
          read-write access to the security node objects and all other objects 
          implemented in the device.  The syntax is defined as an OCTET STRING 
          and therefore any character can have a value of 0..255."
     DEFVAL { "administrator" }
     ::= { security 1 }

-- A.8.2. Maximum Community Names Parameter
communityNamesMax     OBJECT-TYPE
     SYNTAX    INTEGER (1..255)
     ACCESS    read-only
     STATUS    mandatory
     DESCRIPTION
          "This object specifies the maximum number of rows that are implemented 
          in the community name table."
     ::= { security 2 }

-- A.8.3. Community Names Table
communityNameTable  OBJECT-TYPE
     SYNTAX    SEQUENCE OF CommunityNameTableEntry
     ACCESS    not-accessible
     STATUS    mandatory
     DESCRIPTION
          "This table defines the community names that can appear in the 
          community name field of the SNMP message and access privileges 
          associated with that community name."
     ::= { security 3 }

communityNameTableEntry  OBJECT-TYPE
     SYNTAX    CommunityNameTableEntry
     ACCESS    not-accessible
     STATUS    mandatory
     DESCRIPTION
          "This is the row index of information in the community name table."
     INDEX     { communityNameIndex }
     ::= { communityNameTable 1}

CommunityNameTableEntry::=SEQUENCE
     {  communityNameIndex       INTEGER,
        communityNameUser        OCTET STRING,
        communityNameAccessMask  Gauge
     }

-- A.8.3.1. Community Name Index Parameter
communityNameIndex  OBJECT-TYPE
     SYNTAX  INTEGER (1..255)
     ACCESS  read-only
     STATUS  mandatory
     DESCRIPTION
          "This object defines the row index into the communityNameTable. This 
          value shall not exceed the communityNamesMax object value."
     ::=  { communityNameTableEntry 1 }

-- A.8.3.2. User Community Name Parameter
communityNameUser  OBJECT-TYPE
     SYNTAX  OCTET STRING (SIZE(6..16))
     ACCESS  read-write
     STATUS  mandatory
     DESCRIPTION
          "This object defines a community name value that a security 
          administrator can assign user read-write access to information (other 
          than security) in a device. A message with this value in the community 
          name field of an SNMP/SFMP message has user access rights as defined in the 
          communityNameAccessMask.  The syntax is defined as an OCTET STRING and 
          therefore any character can have a value of 0..255."
     DEFVAL  { "public" }
     ::=  { communityNameTableEntry 2 }

-- A.8.3.3. User Community Name Mask Parameter
communityNameAccessMask OBJECT-TYPE
     SYNTAX  Gauge 
     ACCESS  read-write
     STATUS  mandatory
     DESCRIPTION
          "This object defines a 32 bit mask that can be used to associate 
          'write access' with a community name.  A value of 0x00 00 00 00 grants 
          the community name user read-only access and overrides any individual 
          object's read-write access clause.  A value of 0xFF FF FF FF grants the 
          community name user read-write access and an individual object's read-
          write access clause applies.  Values other than 0x00 00 00 00 and 0xFF FF FF FF 
          are implementation specific and may limit viewing and/or accessing the 
          information in a device."
     DEFVAL  { 4294967295 }
     ::= { communityNameTableEntry 3 }


END
