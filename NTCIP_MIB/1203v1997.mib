--******************************************************************************
-- Filename:   1203v1997.MIB
-- Source:      NTCIP 1203:1997
--              
-- Description: This MIB defines the Dynamic Message Sign Objects
-- MIB Revision History:
--  01/01/98    Preliminary Release of TS 3.6 DMS-MIB MIB formatted for 80
--              columns and no TABs
--              In 2.4.1.1.1.2.1 >> changed read-write-only to read-only
--              In 2.5.1.1.1.6, 2.5.1.1.1.8, 2.5.1.1.1.9, and 2.5.1.1.1.10 >>
--              changed read write-write to read-write
--              In 2.5.1.1.1.7 >> corrected ACCESS
--  07/08/98    Added Copyright Notice
--  03/09/00    Reversed edits for SMIC Compiler
--                     Changed filename and copyright years
--                    Changed the import of where Display String comes from
--  08/09/00    Modified header format and wording of copyright and MIB
--                     Distribution Notice
--                     Changed experimental to nemaExperimental per NTCIP 1101(SMI)
--                     Amendment 
-- 11/23/04     Filename was 1203(DMS).MIB
--                     Replaced: 
--                       nemaExperimental
--                       FROM NEMA_SMI
--                       OwnerString, devices, DisplayString
--                           FROM TMIB-II;nemaExperimental
--                     and 
--                        dms OBJECT IDENTIFIER ::= {devices 3}
--                     with:
--                        dms, nemaExperimental, OwnerString
--                             FROM NTCIP8004-A-2004 DEFINITIONS
--Copyright 1997-2000 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--Except for the MIB, Do not copy without written permission of either AASHTO,
--ITE, or NEMA.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned 
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************


--2.1     DYNAMIC MESSAGE SIGNS (DMS) OBJECTS

DMS-MIB DEFINITIONS ::= BEGIN
IMPORTS
  IpAddress, Counter
      FROM RFC1155-SMI
  OBJECT-TYPE
      FROM RFC-1212
  DisplayString
      FROM RFC1213-MIB
--  nemaExperimental
--  FROM NEMA_SMI
--  OwnerString, devices, DisplayString
--  FROM TMIB-II;
  
 dms, nemaExperimental, OwnerString 
      FROM NTCIP8004-A-2004;

--For the purpose of this section, the following OBJECT IDENTIFIERS are used:
--the node location is: nema / transportation
--  dms OBJECT IDENTIFIER ::= {devices 3}

-- Additionally, OBJECT IDENTIFIERS for the Auxiliary objects (see section
-- 2.7.3) which are located under:
 exp-global OBJECT IDENTIFIER ::= {nemaExperimental 1}


MessageIDCode ::= OCTET STRING (SIZE(5))
-- The MessageIDCode consists of those parameters required to define a
-- message within a dmsMessageTable.
-- MsgMemoryType 8 bits       bit 0 to 7
-- MessageNumber 16 bits      bit 8 to 23
-- MessageCRC    16 bits      bit 24 to 39


-- The fields are defined below.

MessageActivationCode ::= OCTET STRING (SIZE(12))
-- The MessageActivationCode consists of those parameters required to activate a
-- message on a DMS.
-- Duration         16 bits      bit 0 to 15
-- ActivatePriority 8 bits       bit 16 to 23
-- MsgMemoryType    8 bits       bit 24 to 31
-- MessageNumber    16 bits      bit 32 to 47
-- MessageCRC       16 bits      bit 48 to 63
-- SourceAddress    32 bits      bit 64 to 95

-- In both cases, bit 0 is the most significant bit (msb) of the most
-- significant byte (MSB).
-- Duration (16 bits) shall indicate the maximum amount of time the message may
-- be displayed
-- prior to activating the dmsDefaultEndDurationMessage.  DmsMsgTimeRemaining
-- shall be set
-- to this value upon successful display of the indicated message.  A Value of
-- 65535 shall
-- indicate an infinite duration.
-- ActivatePriority (8 bits) shall indicate the Activation Priority of the
-- message. If this value is
-- greater than the dmsMsgRunTimePriority of the currently displayed message,
-- the new message
-- shall be displayed unless errors are detected.
-- MsgMemoryType (8 bits) shall indicate the dmsMsgMemoryType of the desired
-- message.
-- MessageNumber (16 bits) shall indicate the dmsMsgNumber of the desired
-- message.
-- MessageCRC (16 bits) shall indicate the dmsMsgMessageCRC of the desired
-- message.
-- Source Address (32 bits) shall indicate the 4-byte IP address of the device
-- which requested the
-- activation.  The dmsActivateMsgError object shall be used to indicate the
-- success or failure of
-- activating any message requested by an object of MessageActivationCode
-- SYNTAX.


--2.2     SIGN CONFIGURATION AND CAPABILITY OBJECTS

dmsSignCfg     OBJECT IDENTIFIER ::= {dms 1}
-- This node is an identifier used to group all objects for DMS sign
-- configurations that are
-- common to all DMS devices.

--2.2.1.1.1.1  Sign Access Parameter
dmsSignAccess   OBJECT-TYPE
SYNTAX    INTEGER (0..255)
ACCESS    read-only
STATUS    mandatory
DESCRIPTION "Indicates the access method to the sign.  Methods that are defined
are:
Bit 0- Other
Bit 1- Walk-in access
Bit 2- Rear access
Bit 3- Front access"
::= {dmsSignCfg 1}


--2.2.1.1.1.2  Sign Type Parameter
dmsSignType   OBJECT-TYPE
SYNTAX    INTEGER{
               other (1),
               bos (2),
               cms (3),
               vmsChar (4),
               vmsLine (5),
               vmsFull (6),
               portableOther (129),
               portableBOS (130),
               portableCMS (131),
               portableVMSChar (132),
               portableVMSLine (133),
               portableVMSFull (134)
               }
ACCESS    read-only
STATUS    mandatory
DESCRIPTION "Indicates the type of sign."
--The descriptions are:
--other:  Device not specified through any other definition, refer to device
--        manual,
--bos: Device is a Blank-Out Sign,
--cms : Device is a Changeable Message Sign,
--vmsChar : Device is a Variable Message Sign with character matrix setup,
--vmsLine :  Device is a Variable Message Sign with line matrix setup,
--vmsFull: Device is a Variable Message Sign with full matrix setup.
--Same is true for all portable signs.
::= {dmsSignCfg 2}


--2.2.1.1.1.3  Sign Height Parameter
dmsSignHeight OBJECT-TYPE
SYNTAX    INTEGER (0..65535)
ACCESS    read-only
STATUS    mandatory
DESCRIPTION "Indicates the sign height in millimeters."
::= {dmsSignCfg 3}


--2.2.1.1.1.4  Sign Width Parameter
dmsSignWidth OBJECT-TYPE
SYNTAX    INTEGER (0..65535)
ACCESS    read-only
STATUS    mandatory
DESCRIPTION "Indicates the Sign Width in millimeters."
::= {dmsSignCfg 4}


--2.2.1.1.1.5  Horizontal Border Parameter
dmsHorizontalBorder OBJECT-TYPE
SYNTAX    INTEGER (0..65535)
ACCESS    read-only
STATUS    mandatory
DESCRIPTION "Indicates the minimum border distance, in millimeters, that exists
on the left and right sides of the sign."
::= {dmsSignCfg 5}


--2.2.1.1.1.6  Sign Vertical Parameter
dmsVerticalBorder   OBJECT-TYPE
SYNTAX    INTEGER (0..65535)
ACCESS    read-only
STATUS    mandatory
DESCRIPTION "Indicates the minimum border distance, in millimeters, that exists
on the top and bottom of the sign."
::= {dmsSignCfg 6}


--2.2.1.1.1.7  Legend Parameter
dmsLegend OBJECT-TYPE
SYNTAX    INTEGER {
               other (1),
               noLegend (2),
               legendExists (3)}
ACCESS    read-only
STATUS    mandatory
DESCRIPTION "Indicates if a Legend is shown on the sign."
::= {dmsSignCfg 7}


--2.2.1.1.1.8  Beacon Type Parameter
dmsBeaconType OBJECT-TYPE
SYNTAX    INTEGER {
               other (1),
               none (2),
               oneBeacon (3),
               twoBeaconSyncFlash (4),
               twoBeaconsOppFlash (5),
               fourBeaconSyncFlash (6),
               fourBeaconAltRowFlash (7),
               fourBeaconAltColumnFlash (8),
               fourBeaconAltDiagonalFlash (9),
               fourBeaconNoSyncFlash (10),
               oneBeaconStrobe (11),
               twoBeaconStrobe (12),
               fourBeaconStrobe (13)}
ACCESS    read-only
STATUS    mandatory
DESCRIPTION
"Indicates the configuration of the type, numbers and flashing patterns of
beacons on a sign."
--The definitions are:
--other: Other types, numbers and patterns of beacons on a sign supported by the
--device
--none: Patterns of beacons not supported by the device
--oneBeacon: 1 beacon flashing
--twoBeaconSyncFlash: 2 beacons, synchronized flashing
--twoBeaconsOppFlash: 2 beacons, opposing flashing
--fourBeaconSyncFlash:  4 beacons, synchronized flashing
--fourBeaconAltRowFlash: 4 beacons, alternate row flashing
--fourBeaconAltColumnFlash: 4 beacons, alternate column flashing
--fourBeaconAltDiagonalFlash: 4 beacons, alternate diagonal flashing
--fourBeaconNoSyncFlash: 4 beacons, no synchronized flashing
--oneBeaconStrobe: 1 beacon, strobe light
--twoBeaconStrobe: two beacons, strobe light
--fourBeaconStrobe: 4 beacons, strobe light
::= {dmsSignCfg 8}


--2.2.1.1.1.9  Sign Technology Parameter
dmsSignTechnology   OBJECT-TYPE
SYNTAX    INTEGER (0..65535)
ACCESS    read-only
STATUS    mandatory
DESCRIPTION "Indicates the utilized technology in a bitmap format  (Hybrids will
have to set the bits for all technologies that the sign utilizes).
Bit 0- Other,
Bit 1- LED,
Bit 2- Flip Disk,
Bit 3- Fiber Optics,
Bit 4- Shuttered,
Bit 5- Lamp,
Bit 6- Drum"
::= {dmsSignCfg 9}


--2.3     VMS CONFIGURATION OBJECTS

vmsCfg  OBJECT IDENTIFIER ::= {dms 2}
-- This subnode is an identifier used to group all objects for support of VMS
-- sign configurations that are common to all VMS devices.


--2.3.1.1.1.1  Character Height in Pixels Parameter
vmsCharacterHeightPixels OBJECT-TYPE
SYNTAX    INTEGER (0..255)
ACCESS    read-only
STATUS    mandatory
DESCRIPTION "Indicates the height of a single character in Pixels.  The value
zero (0) Indicates a variable character height."
::= {vmsCfg 1}


--2.3.1.1.1.2  Character Width in Pixels Parameter
vmsCharacterWidthPixels OBJECT-TYPE
SYNTAX    INTEGER (0..255)
ACCESS    read-only
STATUS    mandatory
DESCRIPTION "Indicates the width of a single character in Pixels. The value zero
(0) indicates a variable character width."
::= {vmsCfg 2}
--A full matrix sign is indicated by a height and width of zero (0).  A line
--matrix sign is indicated by a width of zero (0).


--2.3.1.1.1.3  Sign Height in Pixels Parameter
vmsSignHeightPixels  OBJECT-TYPE
SYNTAX    INTEGER (0..65535)
ACCESS    read-only
STATUS    mandatory
DESCRIPTION "Indicates the number of rows of pixels for the entire sign."
::= {vmsCfg 3}
--To determine the number of lines for a line matrix or character matrix sign,
--divide the vmsSignHeightPixels object value by the vmsCharacterHeightPixels
--object value. This should result in a whole number, the number of lines for
--the sign.


--2.3.1.1.1.4  Sign Width in Pixels Parameter
vmsSignWidthPixels OBJECT-TYPE
SYNTAX    INTEGER (0..65535)
ACCESS    read-only
STATUS    mandatory
DESCRIPTION "Indicates the number of columns of pixels for the entire sign."
::= {vmsCfg 4}
--To determine the number of characters for a character matrix sign, divide the
--vmsSignWidthPixels object value by the vmsCharacterWidthPixels object value.
--This should result in a whole number, the number of characters per line for
--the sign.


--2.3.1.1.1.5  Horizontal Pitch Parameter
vmsHorizontalPitch OBJECT-TYPE
SYNTAX    INTEGER (0..255)
ACCESS    read-only
STATUS    mandatory
DESCRIPTION "Indicates the horizontal distance from the center of one pixel to
the center of the neighboring pixel in millimeters."
::= {vmsCfg 5}


--2.3.1.1.1.6  Vertical Pitch Parameter
vmsVerticalPitch OBJECT-TYPE
SYNTAX    INTEGER (0..255)
ACCESS    read-only
STATUS    mandatory
DESCRIPTION "Indicates the vertical distance from the center of one pixel to the
center of the neighboring pixel in millimeters."
::= {vmsCfg 6}
--If a central figures out that the sign is a character matrix sign, then it
--should automatically impose some space between the characters.  The same is
--valid for line matrix signs.


--2.4     FONT DEFINITION OBJECTS

fontDefinition OBJECT IDENTIFIER ::= {dms 3}
-- This node is an identifier used to group all objects for DMS font
-- configurations that are common to DMS devices.


--2.4.1.1.1.1  Number of Fonts Parameter
numFonts   OBJECT-TYPE
SYNTAX    INTEGER (0..255)
ACCESS    read-only
STATUS    mandatory
DESCRIPTION "Indicates the maximum number of fonts that the sign can store."
::= {fontDefinition 1}


--2.4.1.1.1.2  Font Table Parameter
fontTable OBJECT-TYPE
SYNTAX    SEQUENCE OF FontEntry
ACCESS    not-accessible
STATUS    mandatory
DESCRIPTION "A table containing the information needed to configure/define a
particular font."
::= {fontDefinition 2}

fontEntry OBJECT-TYPE
SYNTAX    FontEntry
ACCESS    not-accessible
STATUS    mandatory
DESCRIPTION "Parameters of the Font Table."
INDEX {fontIndex}
::= {fontTable 1}

FontEntry ::= SEQUENCE {
  fontIndex         INTEGER,
  fontNumber        INTEGER,
  fontName          DisplayString,
  fontHeight        INTEGER,
  fontCharSpacing   INTEGER,
  fontLineSpacing   INTEGER,
  fontVersionID     INTEGER}

--2.4.1.1.1.2.1     Font Index Parameter
fontIndex   OBJECT-TYPE
SYNTAX    INTEGER (1..255)
ACCESS    read-only
STATUS    mandatory
DESCRIPTION "Indicates the row number of the entry."
::= {fontEntry 1}


--2.4.1.1.1.2.2     Font Number Parameter
fontNumber   OBJECT-TYPE
SYNTAX    INTEGER (1..255)
ACCESS    read-write
STATUS    mandatory
DESCRIPTION "A unique, user-specified number for a particular font which can be
different from the value of the fontIndex-object.  This is the number referenced
by MULTI when specifying a particular font.  A device shall return a GenError if
this value is not unique."
::= {fontEntry 2}


--2.4.1.1.1.2.3     Font Name Parameter
fontName   OBJECT-TYPE
SYNTAX    DisplayString (SIZE (0..64))
ACCESS    read-write
STATUS    mandatory
DESCRIPTION "Indicates the name of the font."
::= {fontEntry 3}


--2.4.1.1.1.2.4     Font Height Parameter
fontHeight   OBJECT-TYPE
SYNTAX    INTEGER (0..255)
ACCESS    read-write
STATUS    mandatory
DESCRIPTION "Indicates the height of the font in pixels. Setting this object to
zero (0) invalidates this fontTable row, and also invalidates all corresponding
entries into the characterTable."
::= {fontEntry 4}


--2.4.1.1.1.2.5     Font Character Spacing Parameter
fontCharSpacing   OBJECT-TYPE
SYNTAX    INTEGER (0..255)
ACCESS    read-write
STATUS    mandatory
DESCRIPTION "Indicates the default horizontal spacing (in pixels) between each
of the characters within the font.  This object only applies to Full Matrix and
Line Matrix VMS.  If the font changes on a line, then the average value of the
two fonts shall be used between sequencial characters.  Character Matrix VMS
shall either set this object to zero (0), or not support this object."
::= {fontEntry 5}


--2.4.1.1.1.2.6     Font Line Spacing Parameter
fontLineSpacing   OBJECT-TYPE
SYNTAX    INTEGER (0..255)
ACCESS    read-write
STATUS    mandatory
DESCRIPTION "Indicates the default vertical spacing (in pixels) between each of
the lines within the font.  This object only applies to Full Matrix. The line
spacing for a line is the largest font line spacing of all fonts used on that
line.  The number of pixels between adjacent lines is the average of the line
spacings of each line. Character Matrix VMS and Line Matrix VMS shall either set
this object to zero (0), or not support this object."
::= {fontEntry 6}


--2.4.1.1.1.2.7     Font Version ID Parameter
fontVersionID   OBJECT-TYPE
SYNTAX    INTEGER (0..65535)
ACCESS    read-only
STATUS    mandatory
DESCRIPTION "Each font that has been downloaded to a sign shall have a
relatively unique ID.  This ID shall be calculated using the CRC-16 algorithm
defined in ISO 3309 and the associated PER-encoded FontVersionByteStream."
--
-- The following 4 definitions are used to define the above referenced
-- FontVersionByteStream.
--
-- Complete definitions for these referenced objects, including size
-- information, is contained elsewhere in this document.
--
-- CharacterInformation describes the characteristics of a single character and
-- defines the objects and order of the objects within one row of
-- CharacterInfoList.
--
-- CharacterInformation ::= SEQUENCE {
--      characterNumber       INTEGER,
--      characterWidth        INTEGER,
--      characterBitmap       OCTET STRING }
--
-- CharacterInfoList describes the characteristics of each defined character
-- within a given font and orders the information by the characterNumber in an
-- increasing format.
--
-- CharacterInfoList ::=  SEQUENCE OF CharacterInformation
--
-- FontInformation describes the characteristics of the font which are common to
-- each character and defines the order in which this information appears when
-- constructing the byte stream
-- which will be used to calculate the CRC. There is only one row of data for
-- this SEQUENCE for a specific font.
--
-- FontInformation ::= SEQUENCE {
--        fontNumber            INTEGER,
--        fontHeight            INTEGER,
--        fontCharSpacing       INTEGER,
--        fontLineSpacing       INTEGER }
--
-- FontVersionByteStream defines the order of information used to construct the
-- byte stream which will be used to calculate the CRC.  It consists of the main
-- font characteristics followed
-- by n rows of CharacterInfoList.  The characterInfoList shall be for the
-- fontNumber indicated within the fontInformation field.
-- CharacterInfoList rows are included in FontVersionByteStream only when the
-- associated characterWidth object value is non-zero.
--
-- FontVersionByteStream ::= SEQUENCE {
--        fontInformation     FontInformation,
--        characterInfoList   CharacterInfoList }
--
::= {fontEntry 7}


-- The following 4 definitions are used to define the above referenced
-- FontVersionByteStream.
--CharacterInformation ::= SEQUENCE {
--        characterNumber     INTEGER,
--        characterWidth      INTEGER,
--        characterBitmap     OCTET STRING }
-- Complete definitions for these fields, including size information, is
-- contained below.
--
--CharacterInfoList ::=  SEQUENCE OF CharacterInformation
-- This list only includes entries for a single fontIndex and where the
-- associated characterWidth value is non-zero
--
--FontInformation ::= SEQUENCE {
--   fontNumber          INTEGER,
--   fontHeight          INTEGER,
--   fontCharSpacing     INTEGER,
--   fontLineSpacing     INTEGER }
--  Complete definitions for these fields, including size information, is
--  contained elsewhere in this document.
--
--FontVersionByteStream ::= SEQUENCE {
--        fontInformation          FontInformation,
--        characterInfoList        CharacterInfoList }
-- The characterInfoList shall be for the fontNumber indicated within the
-- fontInformation field.


--2.4.1.1.1.3  Maximum Characters per Font Parameter
maxFontCharacters OBJECT-TYPE
SYNTAX    INTEGER (1..65535)
ACCESS    read-only
STATUS    mandatory
DESCRIPTION "Indicates the maximum number of rows in the character table that
can exist for any given font."
::= {fontDefinition 3}


--2.4.1.1.1.4  Character Table Parameter
characterTable OBJECT-TYPE
SYNTAX    SEQUENCE OF CharacterEntry
ACCESS    not-accessible
STATUS    mandatory
DESCRIPTION "A table containing the information needed to configure/define each
character of a particular font."
::= {fontDefinition 4}


characterEntry OBJECT-TYPE
SYNTAX    CharacterEntry
ACCESS    not-accessible
STATUS    mandatory
DESCRIPTION "Parameters of the Character Configuration Table."
INDEX {fontIndex, characterNumber}
::= {characterTable 1}

CharacterEntry ::= SEQUENCE {
  characterNumber   INTEGER,
  characterWidth    INTEGER,
  characterBitmap   OCTET STRING}


--2.4.1.1.1.4.1     Character Number Parameter
characterNumber   OBJECT-TYPE
SYNTAX    INTEGER (1..65535)
ACCESS    read-only
STATUS    mandatory
DESCRIPTION "Indicates the binary value associated with this character of this
font. For example, if the font set followed the ASCII numbering scheme, the
character giving the bitmap of `A' would be characterNumber 65 (41 hex)."
::= {characterEntry 1}


--2.4.1.1.1.4.2     Character Width Parameter
characterWidth   OBJECT-TYPE
SYNTAX    INTEGER (0..255)
ACCESS    read-write
STATUS    mandatory
DESCRIPTION "Indicates the width of this character in pixels.  A width of zero
(0) indicates this row is invalid."
::= {characterEntry 2}


--2.4.1.1.1.4.3     Character Bitmap Parameter
characterBitmap  OBJECT-TYPE
SYNTAX    OCTET STRING
ACCESS    read-write
STATUS    mandatory
DESCRIPTION "A bitmap that defines each pixel within a rectangular region as
being either ON (bit=1) or OFF (bit=0). The result of this bitmap is how the
character appears on the sign."
--The octet string is treated as a binary bit string. The most significant bit
--defines the state of the pixel in the upper left corner of the rectangular
--region.  The rectangular region is processed by
--rows, left to right, then top to bottom.  The size of the rectangular region
--is defined by the fontHeight and characterWidth objects. After the rectangular
--region is defined, any remaining bits shall be zero (0).
::= {characterEntry 3}


--2.5     MULTI CONFIGURATION OBJECTS

multiCfg  OBJECT IDENTIFIER ::= {dms 4}
-- This subnode is an identifier used to group all objects for support of MULTI
-- language configuration such as all default tag values.


--2.5.1.1.1.1  Default Background Color Parameter
defaultBackgroundColor   OBJECT-TYPE
SYNTAX    INTEGER (0..255)
ACCESS    read-write
STATUS    mandatory
DESCRIPTION "Indicates the color of the background shown on the sign. The
allowed values are:
black (0),
red (1),
yellow (2),
green(3),
cyan (4),
blue (5),
magenta (6),
white (7),
orange (8),
amber (9).
Each of the background colors on a sign should map to one of the colors listed.
If a color is requested that is not supported, then a GenError shall be
returned."
::= { multiCfg 1}


--2.5.1.1.1.2  Default Foreground Color Parameter
defaultForegroundColor   OBJECT-TYPE
SYNTAX    INTEGER (0..255)
ACCESS    read-write
STATUS    mandatory
DESCRIPTION "Indicates the color of the foreground (the actual text) shown on
the sign.  The allowed values are:
black (0),
red (1),
yellow (2),
green(3),
cyan (4),
blue (5),
magenta (6),
white (7),
orange (8),
amber (9).
Each of the colors on a sign should map to one of the colors listed.  If a color
is requested that is not supported, then a GenError shall be returned."
::= {multiCfg 2}


--2.5.1.1.1.3  Default Flash On Time Parameter
defaultFlashOn   OBJECT-TYPE
SYNTAX    INTEGER (0..255)
ACCESS    read-write
STATUS    optional
DESCRIPTION "Indicates the default flash on time, in tenths of a second, for
flashing text.  If the time is set to zero (0), the default is NO FLASHing but
the text remains visible."
::= { multiCfg 3}


--2.5.1.1.1.4  Default Flash Off Time Parameter
defaultFlashOff   OBJECT-TYPE
SYNTAX    INTEGER (0..255)
ACCESS    read-write
STATUS    optional
DESCRIPTION "Indicates the default flash off time, in tenths of a second, for
flashing text.  If the time is set to zero (0), the default is NO FLASHing but
the text remains visible."
::= { multiCfg 4}


--2.5.1.1.1.5  Default Font Parameter
defaultFont   OBJECT-TYPE
SYNTAX    INTEGER (1..255)
ACCESS    read-write
STATUS    mandatory
DESCRIPTION "Indicates the default font number (fontNumber-object) for a
message."
::= { multiCfg 5}


--2.5.1.1.1.6  Default Line Justification Parameter
defaultJustificationLine   OBJECT-TYPE
SYNTAX    INTEGER {
                other(1),
                left(2),
                center(3),
                right(4),
                full(5) }
ACCESS    read-write
STATUS    mandatory
DESCRIPTION "Indicates the default line justification for a message."
::= {multiCfg 6}


--2.5.1.1.1.7  Default Page Justification Parameter
defaultJustificationPage   OBJECT-TYPE
SYNTAX    INTEGER {
                other(1),
                top(2),
                middle(3),
                bottom(4) }
ACCESS    read-write
STATUS    mandatory
DESCRIPTION "Indicates the default page justification for a message."
::= {multiCfg 7}


--2.5.1.1.1.8  Default Page On Time Parameter
defaultPageOnTime   OBJECT-TYPE
SYNTAX    INTEGER (1..255)
ACCESS    read-write
STATUS    mandatory
DESCRIPTION "Indicates the default page on time, in tenths (1/10) of a second.
If the message is only one page, this value is ignored, and the page is
continuously displayed."
::= {multiCfg 8}


--2.5.1.1.1.9  Default Page Off Time Parameter
defaultPageOffTime OBJECT-TYPE
SYNTAX    INTEGER (0..255)
ACCESS    read-write
STATUS    mandatory
DESCRIPTION "Indicates the default page off time, in tenths (1/10) of a second.
If the message is only one page, this value is ignored, and the page is
continuously displayed."
::= {multiCfg 9}


--2.5.1.1.1.10 Default Character Set Parameter
defaultCharacterSet OBJECT-TYPE
SYNTAX    INTEGER {
                other (1),
                eightBit (2)}
ACCESS    read-write
STATUS    mandatory
DESCRIPTION "Indicates the default number of bits used to define a single
character in a MULTI string.
other - a character size other than those listed below, refer to the device
manual.
eightBit - each characterNumber of a given font is encoded as an 8-bit value."
::= {multiCfg 10}
--The intent of this object is to provide a mechanism by which 16-bit character
--sets (and potentially other character sets ) can be supported in a future
--version. Currently, this object only provides a standard for 8-bit character
--encoding.


--2.6     MESSAGE OBJECTS

dmsMessage  OBJECT IDENTIFIER ::= {dms 5}
-- This node is an identifier used to group all objects for support of DMS
-- Message Table functions that are common to DMS devices.


--2.6.1.1.1.1  Number of Permanent Messages Parameter
dmsNumPermanentMsg   OBJECT-TYPE
SYNTAX    INTEGER (0..65535)
ACCESS    read-only
STATUS    mandatory
DESCRIPTION "Indicates the current number of Messages stored in non-volatile,
non-changeable memory (e.g., EPROM).  For CMS and BOS, this is the number of
different messages that can be assembled."
::= {dmsMessage 1}


--2.6.1.1.1.2  Number of Changeable Messages Parameter
dmsNumChangeableMsg   OBJECT-TYPE
SYNTAX    INTEGER (0..65535)
ACCESS    read-only
STATUS    mandatory
DESCRIPTION "Indicates the current number of Messages stored in non-volatile,
changeable memory.  For CMS and BOS, this number shall be zero (0)."
::= {dmsMessage 2}


--2.6.1.1.1.3  Maximum Number of Changeable Messages Parameter
dmsMaxChangeableMsg   OBJECT-TYPE
SYNTAX    INTEGER (0..65535)
ACCESS    read-only
STATUS    mandatory
DESCRIPTION "Indicates the maximum number of Messages that the sign can store in
non-volatile, changeable memory. For CMS and BOS, this number shall be zero
(0)."
::= {dmsMessage 3}


--2.6.1.1.1.4  Free Bytes within Changeable Memory Parameter
dmsFreeChangeableMemory   OBJECT-TYPE
SYNTAX    INTEGER (0..4294967295)
ACCESS    read-only
STATUS    mandatory
DESCRIPTION "Indicates the number of bytes available within non-volatile,
changeable memory. For CMS and BOS, this number shall be zero (0)."
::= {dmsMessage 4}


--2.6.1.1.1.5  Number of Volatile Messages Parameter
dmsNumVolatileMsg   OBJECT-TYPE
SYNTAX    INTEGER (0..65535)
ACCESS    read-only
STATUS    mandatory
DESCRIPTION "Indicates the current number of Messages stored in volatile,
changeable memory. For CMS and BOS, this number shall be zero (0)."
::= {dmsMessage 5}


--2.6.1.1.1.6  Maximum Number of Volatile Messages Parameter
dmsMaxVolatileMsg   OBJECT-TYPE
SYNTAX    INTEGER (0..65535)
ACCESS    read-only
STATUS    mandatory
DESCRIPTION "Indicates the maximum number of Messages that the sign can store in
volatile, changeable memory. For CMS and BOS, this number shall be zero (0)."
::= {dmsMessage 6}


--2.6.1.1.1.7  Free Bytes within Volatile Memory Parameter
dmsFreeVolatileMemory   OBJECT-TYPE
SYNTAX    INTEGER (0..4294967295)
ACCESS    read-only
STATUS    mandatory
DESCRIPTION "Indicates the number of bytes available within volatile, changeable
memory. For CMS and BOS, this number shall be zero (0)."
::= {dmsMessage 7}


--2.6.1.1.1.8  Message Table Parameter
dmsMessageTable OBJECT-TYPE
SYNTAX    SEQUENCE OF DmsMessageEntry
ACCESS    not-accessible
STATUS    mandatory
DESCRIPTION "A table containing the information needed to activate a Message on
a sign.  The values of a columnar object (except the dmsMessageStatus) cannot be
changed when the `dmsMessageStatus'-object of that particular row has the value
of `valid'."
::= {dmsMessage 8}

dmsMessageEntry OBJECT-TYPE
SYNTAX    DmsMessageEntry
ACCESS    not-accessible
STATUS    mandatory
DESCRIPTION "Parameters of the Message Table."
INDEX {dmsMessageMemoryType, dmsMessageNumber}
::= {dmsMessageTable 1}

DmsMessageEntry ::= SEQUENCE {
               dmsMessageMemoryType          INTEGER,
               dmsMessageNumber              INTEGER,
               dmsMessageMultiString         OCTET STRING,
               dmsMessageOwner               OwnerString,
               dmsMessageCRC                 INTEGER,
               dmsMessageBeacon              INTEGER,
               dmsMessagePixelService        INTEGER,
               dmsMessageRunTimePriority     INTEGER,
               dmsMessageStatus              INTEGER
               }


--2.6.1.1.1.8.1     Message Memory Type Parameter
dmsMessageMemoryType  OBJECT-TYPE
SYNTAX    INTEGER {
               other (1),
               permanent (2),
               changeable (3),
               volatile (4),
               currentBuffer (5),
               schedule (6)
               }
ACCESS    read-only
STATUS    mandatory
DESCRIPTION "Indicates the memory-type used to store a  message. Also provides
access to current message (currentBuffer) and currently scheduled message
(schedule)."
-- The definitions of the enumerated values are:
-- other - any other type of memory type that is not listed within one of the
-- values below, refer to device manual;
-- permanent - non-volatile and non-changeable;
-- changeable - non-volatile and changeable;
-- volatile - volatile and changeable;
-- currentBuffer - contains the information regarding the currently displayed
-- message.  Only one entry in the table can have the value of currentBuffer and
-- the value of the dmsMessageNumber
-- object must be one (1);
-- schedule - this entry contains information regarding the currently scheduled
-- message as determined by the time-base scheduler (if present).  Only one
-- entry in the table can have the
-- value of `schedule' and the dmsMessageNumber-object-value for this entry must
-- be 1.  This will be the displayed message when the dmsMessageSourceMode is
-- timebasedScheduler.
::= {dmsMessageEntry 1}


--2.6.1.1.1.8.2     Message Number Parameter
dmsMessageNumber   OBJECT-TYPE
SYNTAX    INTEGER (1..65535)
ACCESS    read-only
STATUS    mandatory
DESCRIPTION "Enumerated listing of row entries within the value of the primary
index to this table (dmsMessageMemoryType -object).  When the primary index is
`currentBuffer' or `schedule', then this value must be one (1)."
::= {dmsMessageEntry 2}


--2.6.1.1.1.8.3     Message MULTI String Parameter
dmsMessageMultiString OBJECT-TYPE
SYNTAX    OCTET STRING
ACCESS    read-write
STATUS    mandatory
DESCRIPTION  "Contains the message written in MULTI-language."
::= {dmsMessageEntry 3}


--2.6.1.1.1.8.4     Message Owner Parameter
dmsMessageOwner  OBJECT-TYPE
SYNTAX    OwnerString
ACCESS    read-write
STATUS    mandatory
DESCRIPTION "Indicates the owner or author of this row."
::= {dmsMessageEntry 4}



--2.6.1.1.1.8.5     Message CRC Parameter
dmsMessageCRC   OBJECT-TYPE
SYNTAX    INTEGER(0..65535)
ACCESS    read-only
STATUS    mandatory
DESCRIPTION "Indicates the CRC-16 (polynominal defined in ISO/IEC 3309) value
created using the values of the dmsMessageMultiString- (MULTI-Message), the
dmsMessageBeacon-, and the dmsMessagePixelService -objects in the order listed,
not including the type or length fields."
::= {dmsMessageEntry 5}


--2.6.1.1.1.8.6     Message Beacon Parameter
dmsMessageBeacon    OBJECT-TYPE
SYNTAX    INTEGER (0..1)
ACCESS    read-write
STATUS    optional
DESCRIPTION "Indicates if connected beacon(s) are to be activated when the
associated message is displayed.  Zero (0) = Beacon(s) are Disabled ;  one (1) =
Beacon(s) are Enabled."
::= {dmsMessageEntry 6}


--2.6.1.1.1.8.7     Message Pixel Service Parameter
dmsMessagePixelService   OBJECT-TYPE
SYNTAX    INTEGER (0..1)
ACCESS    read-write
STATUS    optional
DESCRIPTION "Indicates whether  pixel service shall be  enabled (1) or disabled
(0) while this message is active."
::= {dmsMessageEntry 7}


--2.6.1.1.1.8.8     Message Run Time Priority Parameter
dmsMessageRunTimePriority   OBJECT-TYPE
SYNTAX    INTEGER (1..255)
ACCESS    read-write
STATUS    mandatory
DESCRIPTION "Indicates the run time priority assigned to a particular message.
The value of 1 indicates the lowest level, the value of 255 indicates the
highest level."
::= { dmsMessageEntry 8}


--2.6.1.1.1.8.9     Message Status Parameter
dmsMessageStatus OBJECT-TYPE
SYNTAX    INTEGER {
                notUsed (1),
                modifying (2),
                validating (3),
                valid (4),
                error (5),
                modifyReq (6),
                validateReq (7),
                notUsedReq (8) }
ACCESS    read-write
STATUS    mandatory
DESCRIPTION  "Indicates  the current state of the message.   This state-machine
allows for defining a message, validating a message, and freeing message use." 
--The  enumerated values can be divided into two types, state values and command
--values.  State values can only be read, a GenErr shall occur if a SET is
--attempted.   Command values can be written  to,  and will cause a state change
--if accepted, and  thus  cannot  be returned.  The states
--and commands are defined as follows:
--notUsed:    This is a state value and indicates that the row does not  contain
--any valid message  data.  Controller memory may or may not be released to free 
--memory pool in this state.   Reading an object from a row when this object is
--set to notUsed in undetermined, i.e., last
--contents,  or  random data may be returned.  Setting any object  (except  this
--object) for a row that is notUsed shall return a GenError.  The only valid
--command in this state is modifyReq.
--modifying:  This is a state value and indicates that the row is being modified
--to define a  message.  Modifying any objects (except this object) can only be
--done when the row is in this state,  otherwise a GenError shall be returned.  
--The valid  commands  in  this state is validateReq
--and notUsedReq.
--validating:   This  is  a state value and indicates  that  the  controller  is
--validating all of the message data  for  the  row.   When  validation  is 
--complete,  the  controller will--automatically change the state
--to either valid (message data is good), or error (some error found within  the
--message data).  The only valid command is the notUsedReq command, which shall
--set the  state to notUsed or return a GenErr.
--valid:   This is a state and indicates the message data is valid and the
--message can be activated.   Activation of a message cannot occur in  any other
--state.   The valid commands in this state are notUsedReq and modifyReq.
--error:   This is a state and indicates that an error was detected  during the
--validation process.  The valid commands in this state are modifyReq and
--notUsedReq.
--modifyReq:  This is a command that indicates the user wishes to modify the row
--to define a message.  A GenError may be returned if the controller is in the
--notUsed state and there is
--insufficient memory to define a new message.  A successful request will change
--the state of the row to modifying.  An unsuccessful request will leave the
--row in the same state as it was prior to the command.  This command can be
--issued while in the notUsed, valid and error states.
--validateReq:  This is a command that indicates the user wishes to validate the
--current message data.  This command can only be issued while the row is in the
--modify  state, else a GenError shall be returned.  A successful request will
--change the state of the  row  to validating.  An
--unsuccessful request will leave the row in the same state as it was prior to
--the command.
--notUsedReq:  This is a command that indicates the user wishes to end use of
--the current message data.  This command can be issued while the row is in the
--modify, validating, valid, and error states.  A successful request will
--change the state of the row to notUsed.  An
--unsuccessful request will leave the row in the same state as it was prior to
--the command.
::= {dmsMessageEntry 9}


--2.6.1.1.2    Validate Message Error Parameter
dmsValidateMessageError OBJECT-TYPE
SYNTAX    INTEGER {
               other (1),
               none (2),
               beacons (3),
               pixelService (4),
               syntaxMULTI (5)
               }
ACCESS    read-only
STATUS    mandatory
DESCRIPTION "This is an error code used to identify why a message was not
validated.  If multiple errors occur, only the first value will be indicated.
The syntaxMULTI error is further detailed in the dmsMultiSyntaxError,
dmsMultiSyntaxErrorPosition and dmsMultiOtherErrorDescription objects."
::= {dmsMessage 9}


--2.7     SIGN CONTROL OBJECTS

signControl  OBJECT IDENTIFIER ::= {dms 6}
-- This node is an identifier used to group all objects for support of DMS sign
-- control functions that are common to DMS devices.


--2.7.1.1.1.1  Control Mode Parameter
dmsControlMode  OBJECT-TYPE
SYNTAX    INTEGER {
               other (1),
               local (2),
               external (3),
               central (4),
               centralOverride (5),
               simulation (6)
               }
ACCESS    read-write
STATUS    mandatory
DESCRIPTION "A value indicating the selected control mode of the sign."
--The availabe modes are:
--other - Other control mode supported by the device (refer to device manual);
--local - Local control mode;
--external - External control mode;
--central - Central control mode
--centralOverride - Central station took control over Local control, even though
--the control switch within the cabinet was set to Local
--simulation  - controller is in a mode where it accepts every command and it
--pretends that it would execute them but this does not happen because the
--controller only simulates."
::= {signControl 1}


--2.7.1.1.1.2  Software Reset Parameter
dmsSWReset OBJECT-TYPE
SYNTAX    INTEGER (0..1)
ACCESS    read-write
STATUS    optional
DESCRIPTION "A software interface to initiates a controller reset.  The
execution of the controller reset shall set this object to the value 0.  Value
zero (0) = no reset, value one (1) = reset."
::= {signControl 2}


--2.7.1.1.1.3  Activate Message Parameter
dmsActivateMessage OBJECT-TYPE
SYNTAX    MessageActivationCode
ACCESS    read-write
STATUS    mandatory
DESCRIPTION "A code indicating the message which the sign shall activate.  The
dmsActivateMsgError object shall be set appropriately when this object is SET.
If a message activation error occurs, the new message shall not be displayed and
a GenErr shall be returned."
::= {signControl 3}


--2.7.1.1.1.4  Message Display Time Remaining Parameter
dmsMessageTimeRemaining OBJECT-TYPE
SYNTAX    INTEGER (0..65535)
ACCESS    read-write
STATUS    optional
DESCRIPTION "Indicates the amount of remaining time in minutes that the current
message shall  be displayed.  The value 65535 indicates an infinite duration.  A
value of zero (0) shall indicate that the current message display duration has
expired."
::= {signControl 4}


--2.7.1.1.1.5  Message Table Source Parameter
dmsMsgTableSource OBJECT-TYPE
SYNTAX    MessageIDCode
ACCESS    read-only
STATUS    mandatory
DESCRIPTION "Identifies the message number used to generate the currently
displayed message. This object is written to by the device when the new message
is loaded into the currentBuffer of the MessageTable.  The currently displayed
message is stored in the currentBuffer, but the information regarding which
message number generated the current message would be lost if not indicated
through this object."
::= {signControl 5}


--2.7.1.1.1.6  Message Requester ID Parameter
dmsMsgRequesterID OBJECT-TYPE
SYNTAX    IpAddress
ACCESS    read-only
STATUS    mandatory
DESCRIPTION "A copy of the source-address field from the dmsActivateMessage-
object used to activate the current message.  If the currrent message was not
activated by the dmsActivateMessage-object, then the value of this object shall
be zero (0)."
REFERENCE "RFC 1155, May 1990"
::= {signControl 6}


--2.7.1.1.1.7  Message Source Mode Parameter
dmsMsgSourceMode   OBJECT-TYPE
SYNTAX    INTEGER {
               other (1),
               local (2),
               external (3),
               otherCom1( 4),
               otherCom2 (5),
               otherCom3 (6),
               otherCom4 (7),
               central (8),
               timebasedScheduler (9),
               powerRecovery (10),
               reset (11),
               commLoss (12),
               powerLoss (13),
               endDuration (14)}
ACCESS    read-only
STATUS    mandatory
DESCRIPTION "Indicates the source that initiated the currently displayed
message."
::= {signControl 7}


--2.7.1.1.1.8  Short Power Loss Recovery Message Parameter
dmsShortPowerRecoveryMessage   OBJECT-TYPE
SYNTAX    MessageIDCode
ACCESS    read-write
STATUS    optional
DESCRIPTION "Indicates the message that is displayed after a short power
recovery of the device.  The length of time that defines a short power loss is
indicated in the dmsShortPowerLossTime-object. "
::= {signControl 8}


--2.7.1.1.1.9  Long Power Loss Recovery Message Parameter
dmsLongPowerRecoveryMessage   OBJECT-TYPE
SYNTAX    MessageIDCode
ACCESS    read-write
STATUS    optional
DESCRIPTION "Indicates the message that is displayed after a power recovery of
the device.  The length of time that defines a long power loss is indicated in
the dmsShortPowerLossTime-object."
::= {signControl 9}


--2.7.1.1.1.10 Short Power Loss Time Definition Parameter
dmsShortPowerLossTime OBJECT-TYPE
SYNTAX    INTEGER (0..65535)
ACCESS    read-write
STATUS    optional
DESCRIPTION "Indicates the time, in seconds, from the start of power loss to the
threshold where a short power loss becomes a long power loss.  If the value is
set to zero (0), all power failures are defined as long power losses."
::= {signControl 10}


--2.7.1.1.1.11 Reset Message Parameter
dmsResetMessage   OBJECT-TYPE
SYNTAX    MessageIDCode
ACCESS    read-write
STATUS    optional
DESCRIPTION "Indicates the message that is displayed after a Reset (either
software or hardware) of the device.  This assumes that the device can
differentiate between a reset and a power loss."
::= {signControl 11}


--2.7.1.1.1.12 Communications Loss Message Parameter
dmsCommunicationsLossMessage OBJECT-TYPE
SYNTAX    MessageIDCode
ACCESS    read-write
STATUS    optional
DESCRIPTION "Indicates the message that is displayed after the loss of
communications to the device. If there is no default message defined after the
duration expires, then the sign goes blank."
::= {signControl 12}


--2.7.1.1.1.13 Communication Loss Time Definition Parameter
dmsTimeCommLoss OBJECT-TYPE
SYNTAX    INTEGER (0..65535)
ACCESS    read-write
STATUS    optional
DESCRIPTION "Defines the maximum time (inclusive), in minutes, between
successive Application Layer messages that can occur before a communication loss
is assumed.  If this object is set to zero (0), no communication loss shall
occur."
::= {signControl 13}
--This timer differs from the Data Link Layer timers (T1 to T4).  A dial-up
--circuit may have short time-outs at the DL Layer, but central might only dial
--up once a month to confirm operation, in
--which case this object would be set to ~ 35 days.


--2.7.1.1.1.14 Power Loss Message Parameter
dmsPowerLossMessage OBJECT-TYPE
SYNTAX    MessageIDCode
ACCESS    read-write
STATUS    optional
DESCRIPTION "Indicates the message that is displayed DURING the loss of power of
the device."
::= {signControl 14}


--2.7.1.1.1.15 End Duration Message Parameter
dmsEndDurationMessage OBJECT-TYPE
SYNTAX    MessageIDCode
ACCESS    read-write
STATUS    optional
DESCRIPTION "Indicates the message that is displayed after the indicated
duration for a message has expired and no other Message had been assigned to
replace the previous Message."
::= {signControl 15}


--2.7.1.1.1.16 Memory Management Parameter
dmsMemoryMgmt OBJECT-TYPE
SYNTAX    INTEGER  {
               other (1),
               normal (2),
               clearChangeableMessages (3),
               clearVolatileMessages (4)
               }
ACCESS    read-write
STATUS    optional
DESCRIPTION "Allows the system to manage the device's memory."
::= {signControl 16}


--2.7.1.1.1.17 Activate Message Error Parameter
dmsActivateMsgError OBJECT-TYPE
SYNTAX    INTEGER {
               other (1),
               none (2),
               priority (3),
               underValidation (4),
               memoryType (5),
               messageNumber (6),
               messageCRC (7),
               syntaxMULTI (8),
               localMode (9)
               }
ACCESS    read-only
STATUS    mandatory
DESCRIPTION "This is an error code used to identify why a message was not
displayed.  If multiple errors occur, only the latest value will be indicated.
The syntaxMULTI error is further detailed in the dmsMultiSyntaxError,
dmsMultiSyntaxErrorPosition and dmsMultiOtherErrorDescription objects."
::= {signControl 17}


--2.7.1.1.1.18 MULTI Syntax Error Parameter
dmsMultiSyntaxError OBJECT-TYPE
SYNTAX    INTEGER {
                other (1),
                none (2),
                unsupportedTag (3),
                unsupportedTagValue (4),
                textTooBig (5),
                fontNotDefined (6),
                characterNotDefined (7),
                fieldDeviceNotExist (8),
                fieldDeviceError (9),
                flashRegionError (10),
                tagConflict (11),
                tooManyPages (12)
                }
ACCESS    read-only
STATUS    mandatory
DESCRIPTION "This is an error code used to identify the first detected syntax
error within the MULTI message."
-- other:                An error other than one of those listed.
-- none:                 No error detected.
-- unsupportedTag:       The referenced tag is not supported by this device.
-- unsupportedTagValue:  The referenced tag value is not supported by this
--                       device.
-- textTooBig:           Too many characters on a line and/or too many lines for
--                       a page.
-- fontNotDefined:       The referenced font is not defined in this device.
-- characterNotDefined:  The referenced character is not defined in the selected
--                       font.
-- fieldDeviceNotExist:  The referenced field device does not exist / is not
--                       connected to this device.
-- fieldDeviceError:     This device is not receiving input from the referenced
--                       field device and/or the refererenced field device has a
--                       fault.
-- flashRegionError:     The flashing region selected cannot be flashed by this
--                       device.
-- tagConflict:          The message cannot be displayed with the combination of
--                       tags and/or tag implementation  cannot be resolved.
-- tooManyPages:         Too many pages of text exists in the message.
::= {signControl 18}


--2.7.1.1.1.19 Position of MULTI Syntax Error Parameter
dmsMultiSyntaxErrorPosition OBJECT-TYPE
SYNTAX    INTEGER (0..65535)
ACCESS    read-only
STATUS    mandatory
DESCRIPTION "This is the offset from the first character (i.e. first character
has offset 0, second is 1, etc.) of the MULTI message where the SYNTAX error
occurred."
::= {signControl 19}


--2.7.1.1.1.20 Description of Other MULTI Error Parameter
dmsMultiOtherErrorDescription OBJECT-TYPE
SYNTAX    DisplayString (SIZE (0..50))
ACCESS    read-write
STATUS    optional
DESCRIPTION "Indicates vendor-specified error message descriptions.  Associated
errors occurred due to vendor-specific MULTI-tag responses."
::= {signControl 20}


--2.7.1.1.1.21 Pixel Service Duration Parameter
vmsPixelServiceDuration OBJECT-TYPE
SYNTAX    INTEGER (0..65535)
ACCESS    read-write
STATUS    optional
DESCRIPTION "Indicates the pixel service duration in seconds."
::= {signControl 21}


--2.7.1.1.1.22 Pixel Service Frequency Parameter
vmsPixelServiceFrequency OBJECT-TYPE
SYNTAX    INTEGER (0..1440)
ACCESS    read-write
STATUS    optional
DESCRIPTION "Indicates the pixel service cycle time (frequency) in minutes."
::= { signControl 22}


--2.7.1.1.1.23 Pixel Service Time Parameter
vmsPixelServiceTime OBJECT-TYPE
SYNTAX    INTEGER (0..1440)
ACCESS    read-write
STATUS    optional
DESCRIPTION "Indicates the base time at which the first pixel service shall
occur.  Time is expressed in minutes from the epoch of Midnight of each day."
::= { signControl 23}


--2.8     ILLUMINATION/BRIGHTNESS OBJECTS

illum  OBJECT IDENTIFIER ::= {dms 7}
-- This node is an identifier used to group all objects supporting DMS sign
-- illumination functions that are common to DMS devices.


--2.8.1.1.1.1  Illumination Control Parameter
dmsIllumControl  OBJECT-TYPE
SYNTAX    INTEGER {
               other (1),
               photocell (2),
               timer (3),
               manual (4)
               }
ACCESS    read-write
STATUS    mandatory
DESCRIPTION "Indicates the method used to select the Brightness Level.
Photocell indicates that the Brightness Level is based on photocell status.
Timer indicates the the Brightness Level is set by an internal timer.  Manual
indicates that the Brightness Level must be changed via the dmsIllumManLevel-
object.  When switching to manual mode from any other mode, the current
brightness level shall automatically be loaded into the dmsIllumManLevel
object."
::= {illum 1}


--2.8.1.1.1.2  Maximum Illumination Photocell Level Parameter
dmsIllumMaxPhotocellLevel   OBJECT-TYPE
SYNTAX    INTEGER (0..65535)
ACCESS    read-only
STATUS    mandatory
DESCRIPTION "Indicates the maximum value given by the
dmsIllumPhotocellLevelStatus-object."
::= {illum 2}


--2.8.1.1.1.3  Status of Illumination Photocell Level Parameter
dmsIllumPhotocellLevelStatus   OBJECT-TYPE
SYNTAX    INTEGER (0..65535)
ACCESS    read-only
STATUS    mandatory
DESCRIPTION "Indicates the level of Ambient Light as a value ranging from 0
(darkest) to the value of dmsIllumMaxPhotocellLevel- object (brightest), based
on the photocell detection."
::= {illum 3}


--2.8.1.1.1.4  Number of Illumination Brightness Levels Parameter
dmsIllumNumBrightLevels   OBJECT-TYPE
SYNTAX    INTEGER (0..255)
ACCESS    read-only
STATUS    mandatory
DESCRIPTION "Indicates the number of individually selectable Brightness Levels
supported by the device, excluding the OFF level."
::= {illum 4}


--2.8.1.1.1.5  Status of Illumination Brightness Level Parameter
dmsIllumBrightLevelStatus   OBJECT-TYPE
SYNTAX    INTEGER (0..255)
ACCESS    read-only
STATUS    mandatory
DESCRIPTION "Indicates the current Brightness Level of the device, ranging from
0 (OFF) to the maximum value given by the dmsIllumNumBrightLevels- object
(Brightest)."
::= {illum 5}


--2.8.1.1.1.6  Illumination Manual Level Parameter
dmsIllumManLevel   OBJECT-TYPE
SYNTAX    INTEGER (0..255)
ACCESS    read-write
STATUS    mandatory
DESCRIPTION "Indicates the desired value of the Brightness Level as a value
ranging from 0 to the value of the dmsIllumNumBrightLevels-object when under
manual control."
::= {illum 6}


--2.8.1.1.1.7  Illumination Brightness Values Parameter
dmsIllumBrightnessValues  OBJECT-TYPE
SYNTAX   OCTET STRING
ACCESS   read-write
STATUS   mandatory
DESCRIPTION "An OCTET STRING describing the sign's Brightness Level in
relationship to the Photocell(s) detection of ambient light.  For each
brightness level, there is a corresponding range of photocell levels.  The
number of levels transmitted is defined by the first byte of the datapacket, but
cannot exceed the value of the dmsIllumNumBrightLevels object. "
--After a SET, an implementation may interpolate these entries to create a table
--with as many entries as needed.  For each level, there are three 16-bit values
--that occur in the following order:
--Brightness point, Photocell level down, Photocell level up.
--The Brightness point is a value between 0 (no light output) and 65535 (maximum
--light output).
--Each step is 1/65535 of the maximum light output (linear scale).
--The Photocell-level-down is the lowest photocell level for this brightness
--level.  Should the photocell level go below this point, the automatic
--brightness level would go down one level.
--The Photocell-level-up is the highest photocell level for this brightness
--level.  Should the photocell level go above this point, the automatic
--brightness level would go up one level.
--The photocell level (Up and Down) values may not exceed the value of the
--dmsIllumMaxPhotocellLevel object."
::= {illum 7}

--The points transmitted should be selected so that there is no photocell level
--which does not have a brightness level.
--Hystersis is possible by defining the photocell-level-up at a level higher
--than the upper level's photocell-level-down.
--The following provides an example of this operation
--  0                   1                   2                   3
--  0 1 2 3 4 5 6 7 8 9 0 1 2 3 4 5 6 7 8 9 0 1 2 3 4 5 6 7 8 9 0 1
-- +-+-+-+-+-+-+-+-+
-- |NumEntries = n |
-- -+-+-+-+-+-+-+-+-+-+-+-+-+-+-+-+-+-+-+-+-+-+-+-+-+-+-+-+-+-+-+-+-+
--       Brightness level 1       |  Photocell-Level-Down point 1   |
-- -+-+-+-+-+-+-+-+-+-+-+-+-+-+-+--+-+-+-+-+-+-+-+-+-+-+-+-+-+-+-+-+
-- |   Photocell-Level-Up point 1       Brightness level 2          |
-- +-+-+-+-+-+-+-+-+-+-+-+-+-+-+-+--+-+-+-+-+-+-+-+-+-+-+-+-+-+-+-+-
-- |   Photocell-Level-Down point 2 |   Photocell-Level-Up point 2
-- +-+-+-+-+-+-+-+-+-+-+-+-+-+-+-+-+-+-+-+-+-+-+-+-+-+-+-+-+-+-+-+-+-
--
-- +-+-+-+-+-+-+-+-+-+-+-+-+-+-+-+-+-+-+-+-+-+-+-+-+-+-+-+-+-+-+-+-+-
-- |   Photocell-Level-Down point n |   Photocell-Level-Up point n
-- +-+-+-+-+-+-+-+-+-+-+-+-+-+-+-+-+-+-+-+-+-+-+-+-+-+-+-+-+-+-+-+-+-


--2.8.1.1.1.8  Brightness Values Error Parameter
dmsIllumBrightnessValuesError OBJECT-TYPE
SYNTAX    INTEGER {
                other (1),
                none (2),
                photocellGap (3),
                negativeSlope (4),
                tooManyLevels (5),
                invalidData (6)
                }
ACCESS    read-only
STATUS    mandatory
DESCRIPTION "Indicates the error encountered when the brightness table was SET."
::= {illum 8}


--2.8.1.1.1.9  Status of Illumination Light Output Parameter
dmsIllumLightOutputStatus   OBJECT-TYPE
SYNTAX    INTEGER (0..65535)
ACCESS    read-only
STATUS    optional
DESCRIPTION "Indicates the current physical light output value ranging from 0
(darkest) to 65535 (maximum output)."
::= {illum 9}


--2.9     SCHEDULING ACTION OBJECTS

dmsSchedule  OBJECT IDENTIFIER ::= {dms 8}
-- This node is an identifier used to group all DMS device-specific objects
-- supporting DMS sign timebased scheduling.


--2.9.1.1.1.1  Action Table Entries Parameter
numActionTableEntries  OBJECT-TYPE
SYNTAX    INTEGER (0..255)
ACCESS    read-only
STATUS    mandatory
DESCRIPTION "Indicates the number of rows that are stored in the
dmsActionTable."
::= {dmsSchedule 1}


--2.9.1.1.1.2  Action Table Parameter
dmsActionTable OBJECT-TYPE
SYNTAX    SEQUENCE OF DmsActionEntry
ACCESS    not-accessible
STATUS    mandatory
DESCRIPTION "A table containing a list of message codes.  The scheduler will
determine when a message shall be displayed.  The dayPlanTable of the scheduler
points to a row in the table to identify the message to be activated."
REFERENCE "TS3.4-1996, timebase-node"
::= {dmsSchedule 2}

dmsActionEntry OBJECT-TYPE
SYNTAX    DmsActionEntry
ACCESS    not-accessible
STATUS    mandatory
DESCRIPTION "Parameters of the DMS Action Table."
INDEX {dmsActionIndex}
::={dmsActionTable 1}

DmsActionEntry ::= SEQUENCE {
  dmsActionIndex    INTEGER,
  dmsActionMsgCode  MessageIDCode}


--2.9.1.1.1.2.1     Action Index Parameter
dmsActionIndex OBJECT-TYPE
SYNTAX    INTEGER (1..255)
ACCESS    read-only
STATUS    mandatory
DESCRIPTION "Enumerated listing of row entries.  The value of this object cannot
exceed the value of the numActionTableEntries - object."
::= {dmsActionEntry 1}

--2.9.1.1.1.2.2     Action Message Code Parameter
dmsActionMsgCode OBJECT-TYPE
SYNTAX    MessageIDCode
ACCESS    read-write
STATUS    mandatory
DESCRIPTION "A number indicating the message memory type, the message number and
the associated message-specific CRC as indicated within the message table."
::= {dmsActionEntry 2}


--2.10    AUXILIARY I/O OBJECTS

auxiliaryIO  OBJECT IDENTIFIER ::= { exp-global 1}
-- Temporarily, this node is logically located under the nema-experimental node
-- (will ultimately be moved to the Global node); it is also an identifier used
-- to group all objects supporting auxiliary IO.


--2.10.1.1.1.1 Maximum Number of Digital Auxiliary IOs Parameter
maxAuxIODigital OBJECT-TYPE
SYNTAX    INTEGER (0..255)
ACCESS    read-only
STATUS    mandatory
DESCRIPTION "The number of rows contained in the `auxIOTable' with the
auxPortType set to `digital'."
::= {auxiliaryIO 1}


--2.10.1.1.1.2 Maximum Number of Analog Auxiliary IOs Parameter
maxAuxIOAnalog OBJECT-TYPE
SYNTAX    INTEGER (0..255)
ACCESS    read-only
STATUS    mandatory
DESCRIPTION "The number of rows contained in the `auxIOTable' with the
auxPortType set to `analog'."
::= {auxiliaryIO 2}


--2.10.1.1.1.3 Auxiliary IO Table Parameter
auxIOTable   OBJECT-TYPE
SYNTAX    SEQUENCE OF AuxIOEntry
ACCESS    not-accessible
STATUS    mandatory
DESCRIPTION "A table providing the means to access the auxiliary I/O of the
Controller, this includes reading inputs and setting outputs.  A maximum of 255
auxiliary IOs can be defined for all, digital, analog or other types of ports."
::= { auxiliaryIO 3}

auxIOEntry OBJECT-TYPE
SYNTAX    AuxIOEntry
ACCESS    not-accessible
STATUS    mandatory
DESCRIPTION "Parameters of the auxiliary IO table."
INDEX {auxIOPortType, auxIOPortNumber}
::={auxIOTable 1}

AuxIOEntry ::= SEQUENCE {
  auxIOPortType          INTEGER,
  auxIOPortNumber        INTEGER,
  auxIODescription       DisplayString,
  auxIOResolution        INTEGER,
  auxIOValue             INTEGER,
  auxIOPortDirection     INTEGER
  }


--2.10.1.1.1.3.1    Auxiliary Port Type Parameter
auxIOPortType OBJECT-TYPE
SYNTAX    INTEGER{
               other (1),
               analog (2),
               digital (3)
               }
ACCESS    read-only
STATUS    mandatory
DESCRIPTION "Indicates the type of auxiliary I/O, which can be analog, digital
or other."
::= {auxIOEntry 1}


--2.10.1.1.1.3.2    Auxiliary Port Number Parameter
auxIOPortNumber OBJECT-TYPE
SYNTAX    INTEGER (1..255)
ACCESS    read-only
STATUS    mandatory
DESCRIPTION "Indicates the port number for the associated port type.  Port
numbers are used sequentially from one to max for each port type.  There can be
a port 1 for analog port and port 1 for digital port."
::= {auxIOEntry 2}


--2.10.1.1.1.3.3    Auxiliary Description Parameter
auxIODescription OBJECT-TYPE
SYNTAX    DisplayString (SIZE (0..50))
ACCESS    read-write
STATUS    mandatory
DESCRIPTION "Informational text field describing the device at the associated
auxiliary I/O"
::= {auxIOEntry 3}



--2.10.1.1.1.3.4    Auxiliary Resolution Parameter
auxIOResolution OBJECT-TYPE
SYNTAX    INTEGER (1..255)
ACCESS    read-write
STATUS    mandatory
DESCRIPTION "Defines number of bits used for the IO-port (e.g. width of digital,
resolution of analog)."
::= {auxIOEntry 4}


--2.10.1.1.1.3.5    Auxiliary Value Parameter
auxIOValue OBJECT-TYPE
SYNTAX    INTEGER (0..4294967295)
ACCESS    read-write
STATUS    mandatory
DESCRIPTION "For input or bidirectional ports, this contains the current value
of the input.  For output ports, this is the last commanded value of the port.
A genError shall be generated, if this object is set and the port is an input."
::= {auxIOEntry 5}


--2.10.1.1.1.3.6    Auxiliary Port Direction Parameter
auxIOPortDirection OBJECT-TYPE
SYNTAX    INTEGER {
               output (1),
               input (2),
               bidirectional (3)}
ACCESS    read-write
STATUS    mandatory
DESCRIPTION "Indicates whether state of this port can be set (output), read
(input) or both (bidirectional)."
::= {auxIOEntry 6}


--2.11    SIGN STATUS OBJECTS

dmsStatus  OBJECT IDENTIFIER ::= {dms 9}
-- This node is an identifier used to group all objects supporting DMS sign
-- status monitoring functions that are common to DMS devices.


--2.11.1.1.1.1 Number of Rows in MULTI Field Table Parameter
statMultiFieldRows OBJECT-TYPE
SYNTAX    INTEGER (0..255)
ACCESS    read-only
STATUS    mandatory
DESCRIPTION "Indicates the number of rows in the statMultiFieldTable that are
currently being used."
::={dmsStatus 1}


--2.11.1.1.1.2 MULTI Field Table Parameter
statMultiFieldTable OBJECT-TYPE
SYNTAX    SEQUENCE OF StatMultiFieldEntry
ACCESS    not-accessible
STATUS    mandatory
DESCRIPTION  "A table containing the currently displayed value of a specified
Field.  The number of rows  is given by the value of statMultiFieldRows-object."
::= { dmsStatus 2}

statMultiFieldEntry OBJECT-TYPE
SYNTAX    StatMultiFieldEntry
ACCESS    not-accessible
STATUS    mandatory
DESCRIPTION "Parameters of the Status Multi Field Table."
INDEX {statMultiFieldIndex}
::={statMultiFieldTable 1}

StatMultiFieldEntry ::= SEQUENCE {
               statMultiFieldIndex           INTEGER,
               statMultiFieldCode            INTEGER,
               statMultiCurrentFieldValue    OCTET STRING}


--2.11.1.1.1.2.1    MULTI Field Index Parameter
statMultiFieldIndex   OBJECT-TYPE
SYNTAX    INTEGER (1..255)
ACCESS    read-only
STATUS    mandatory
DESCRIPTION  "The index number into this table indicating the sequential order
of the field within the MULTI-string."
::= {statMultiFieldEntry 1}


--2.11.1.1.1.2.2    Code of MULTI Field Parameter
statMultiFieldCode   OBJECT-TYPE
SYNTAX    INTEGER (1..255)
ACCESS    read-only
STATUS    mandatory
DESCRIPTION  "Indicates the ID of the value of the statMultiCurrrentFieldValue-
object.  The field codes are indicated under the `Field'-tag in MULTI (see
section 3)."
::= {statMultiFieldEntry 2}


--2.11.1.1.1.2.3    Current Value of the MULTI Field Parameter
statMultiCurrentFieldValue   OBJECT-TYPE
SYNTAX    OCTET STRING (SIZE (0..50))
ACCESS    read-only
STATUS    mandatory
DESCRIPTION  "Indicates the currently displayed text of the MULTI-message for
the corresponding Field."
::= {statMultiFieldEntry 3}


--2.11.1.1.1.3 Current Speed Parameter
dmsCurrentSpeed  OBJECT-TYPE
SYNTAX    INTEGER (0..255)
ACCESS    read-only
STATUS    optional
DESCRIPTION  "Used to retrieve the current speed value as detected by the
attached device.  The speed is transmitted in kilometers per hour (km/h).  This
value may vary from the displayed speed value due to application specific
implementation."
::= { dmsStatus 3}


--2.11.1.1.1.4 Current Speed Limit Parameter
dmsCurrentSpeedLimit  OBJECT-TYPE
SYNTAX    INTEGER (0..255)
ACCESS    read-write
STATUS    optional
DESCRIPTION  "Indicates the current speed limit in kilometers per hour (km/h)."
::= { dmsStatus 4}


--2.11.1.1.1.5 Watchdog Failure Count Parameter
watchdogFailureCount  OBJECT-TYPE
SYNTAX    Counter
ACCESS    read-only
STATUS    optional
DESCRIPTION "An ASN.1 Counter indicating the number of watchdog failures that
have occurred."
::= { dmsStatus 5}


--2.11.1.1.1.6 Open Door Status Parameter
dmsStatDoorOpen  OBJECT-TYPE
SYNTAX    INTEGER (0..255)
ACCESS    read-only
STATUS    optional
DESCRIPTION "Indicates whether any of the doors to the controller cabinet or the
sign housing are open. This is a bitmap; if a bit is set (= 1) then the door is
open; if a bit not is not set, then the associated door is closed."
::= { dmsStatus  6}


--2.11.2  Status Error Objects
statError  OBJECT IDENTIFIER ::= {dmsStatus 7}
-- This node is an identifier used to group all objects supporting DMS sign
-- message error status functions that are common to DMS devices.


--2.11.2.1.1.1 Short Error Status Parameter
shortErrorStatus  OBJECT-TYPE
SYNTAX    INTEGER (0..65535)
ACCESS    read-only
STATUS    mandatory
DESCRIPTION "A bitmap of summary errors where the bits are defined as follows:
Bit 0- other error
Bit 1- communications error
Bit 2- power error
Bit 3- attached device error
Bit 4- lamp error
Bit 5- pixel error
Bit 6- photocell error
Bit 7- message error
Bit 8- controller error
Bit 9- temperature warning
Bit 10- fan error
If a bit is set to one (1), then the associated error is existing; if the bit is
set to zero (0), then the associated error is not existing."
::= {statError 1}


--2.11.2.1.1.2 Number of Rows in Pixel Failure Table Parameter
pixelFailureTableNumRows OBJECT-TYPE
SYNTAX    INTEGER (0..65535)
ACCESS    read-only
STATUS    mandatory
DESCRIPTION "The number of rows contained in the pixelFailureTable each
indicating failed pixels."
::= { statError 2}


--2.11.2.1.1.3 Pixel Failure Table Parameter
pixelFailureTable   OBJECT-TYPE
SYNTAX    SEQUENCE OF PixelFailureEntry
ACCESS    not-accessible
STATUS    mandatory
DESCRIPTION "A table containing the X and Y location of a failed pixel.  The
number of rows is given by the value of pixelFailureTableNumRows -object."
::= { statError 3}

pixelFailureEntry   OBJECT-TYPE
SYNTAX    PixelFailureEntry
ACCESS    not-accessible
STATUS    mandatory
DESCRIPTION "Parameters of the Pixel Failure Table.  The detection of pixel
failures during message displays shall be appended to the end of the table."
INDEX { pixelFailureDetectionType, pixelFailureIndex}
::= {pixelFailureTable 1}

PixelFailureEntry ::= SEQUENCE {
  pixelFailureDetectionType   INTEGER,
  pixelFailureIndex           INTEGER,
  pixelFailureXLocation       INTEGER,
  pixelFailureYLocation       INTEGER,
  pixelFailureStatus          INTEGER}


--2.11.2.1.1.3.1    Pixel Failure Detection Type Parameter
pixelFailureDetectionType  OBJECT-TYPE
SYNTAX    INTEGER {
                other (1),
                pixelTest (2),
                messageDisplay(3)
                }
ACCESS    read-only
STATUS    mandatory
DESCRIPTION "Indicates the type of test/display that leads to the pixel failure
entry."
::= {pixelFailureEntry 1}


--2.11.2.1.1.3.2    Pixel Failure Index Parameter
pixelFailureIndex   OBJECT-TYPE
SYNTAX    INTEGER (1..65535)
ACCESS    read-only
STATUS    mandatory
DESCRIPTION "Enumerated listing of row entries."
::= {pixelFailureEntry 2}


--2.11.2.1.1.3.3    Pixel Failure X Location Parameter
pixelFailureXLocation   OBJECT-TYPE
SYNTAX    INTEGER (1..65535)
ACCESS    read-only
STATUS    mandatory
DESCRIPTION "Indicates the X location of the failed pixel.  The X direction is
the horizontal direction.  The X location is counted from the left-most pixel in
number of pixels."
::= {pixelFailureEntry 3}


--2.11.2.1.1.3.4    Pixel Failure Y Location Parameter
pixelFailureYLocation   OBJECT-TYPE
SYNTAX    INTEGER (1..65535)
ACCESS    read-only
STATUS    mandatory
DESCRIPTION "Indicates the Y location of the failed pixel.  The Y direction is
the vertical direction.  The Y location is counted from the top-most pixel in
number of pixels."
::= {pixelFailureEntry 4}


--2.11.2.1.1.3.5    Pixel Failure Status Parameter
pixelFailureStatus   OBJECT-TYPE
SYNTAX    INTEGER (0..255)
ACCESS    read-only
STATUS    mandatory
DESCRIPTION  "Indicates the current status of the specified pixel and the
operation which made this determination. This is a bit field with the following
format:
Bit 0  0: Stuck Off / 1: Stuck On
Bit 1  0: No Color Error / 1: Color Error
Bit 2     0: no electrical error / 1: electrical error
Bit 3     0: no mechanical error / 1: mechanical error
"
::= {pixelFailureEntry 5}


--2.11.2.1.1.4 Pixel Test Activation Parameter
pixelTestActivation   OBJECT-TYPE
SYNTAX    INTEGER {
                other (1),
                noTest (2),
                test (3),
                clearTable (4)
                }
ACCESS    read-write
STATUS    mandatory
DESCRIPTION  "Indicates the state of the pixel testing.  The actual test routine
can vary among different manufacturers.  The results of the pixel failure test
shall be stored in the pixel failure table.  The pixel failure table will be
cleared, when a pixel test is started (test).  Setting the value to test will
start the test, meaning this test will be executed once.  The sign controller
will automatically set the value of this object back to noTest after
completion."
::= {statError 4}


--2.11.2.1.1.5 Stuck On Lamp Failure Parameter
lampFailureStuckOn   OBJECT-TYPE
SYNTAX    OCTET STRING (SIZE (0..255))
ACCESS    read-only
STATUS    mandatory
DESCRIPTION  "Indicates whether each lamp within the sign is stuck on as a
bitmap.  If a lamp is stuck on, its associated bit is set to one (1)."
::= { statError 5}


--2.11.2.1.1.6 Stuck Off Lamp Failure Parameter
lampFailureStuckOff   OBJECT-TYPE
SYNTAX    OCTET STRING (SIZE (0..255))
ACCESS    read-only
STATUS    mandatory
DESCRIPTION  "Indicates whether each lamp within the sign is stuck off as a
bitmap.  If a lamp is stuck off, its associated bit is set to one (1)."
::= { statError 6}


--2.11.2.1.1.7 Lamp Test Activation Parameter
lampTestActivation   OBJECT-TYPE
SYNTAX    INTEGER {
                other (1),
                noTest (2),
                test (3)
                }
ACCESS    read-write
STATUS    mandatory
DESCRIPTION  "Indicates the state of the lamp testing. The actual test routine
can vary among different manufacturers.  The results of the lamp failure test
shall be stored appropriately, either in the lampFailureStuckOn- or in the
lampFailureStuckOff-objects. Setting the value to test will start the test,
meaning this test will be executed once.  The sign controller shall
automatically set the value of this object back to noTest after completion."
::= {statError 7}


--2.11.2.1.1.8 Fan Failure Parameter
fanFailures OBJECT-TYPE
SYNTAX    OCTET STRING (SIZE (0..4))
ACCESS    read-only
STATUS    optional
DESCRIPTION "Indicates whether each fan (system) within a DMS is capable of
operating, expressed as a bitmap.  If a fan (system) failed, its associated bit
is set to one (1)."
::= {statError 8}


--2.11.2.1.1.9 Fan Test Activation Parameter
fanTestActivation   OBJECT-TYPE
SYNTAX    INTEGER {
                other (1),
                noTest (2),
                test (3)
                }
ACCESS    read-write
STATUS    optional
DESCRIPTION  "Indicates the state of the fan testing. The actual test routine
can vary among different manufacturers.  The results of the fan test shall be
stored in either the fanFailures-objects. Setting the value to test will start
the test, meaning this test will be executed once.  The sign controller will
automatically set the value of this object back to noTest after completion."
::= {statError 9}


--2.11.2.1.1.10     Controller Error Status Parameter
controllerErrorStatus  OBJECT-TYPE
SYNTAX    INTEGER (0..255)
ACCESS    read-only
STATUS    mandatory
DESCRIPTION "A bitmap of controller related errors where the bits are defined as
follows:
Bit 0- other controller error
Bit 1- PROM error
Bit 2- program/processor error
Bit 3- RAM error
If a bit is set to one (1), then the associated error is existing; if the bit is
set to zero (0), then the associated error is not existing."
::= {statError 10}


--2.11.3  Power Status Objects
statPower  OBJECT IDENTIFIER ::= {dmsStatus 8}
-- This node is an identifier used to group all objects supporting DMS sign
-- power status monitoring functions that are common to DMS devices.


--2.11.3.1.1.1 Sign Volts Parameter
signVolts OBJECT-TYPE
SYNTAX    INTEGER (0..65535)
ACCESS    read-only
STATUS    optional
DESCRIPTION "A voltage measurement in units of hundredth (1/100) of a volt.  The
maximum value (0xFFFF) corresponds to a voltage of 655.35 volts.  This is an
indication of the sign battery voltage."
::= {statPower 1}


--2.11.3.1.1.2 Low Fuel Threshold Parameter
lowFuelThreshold OBJECT-TYPE
SYNTAX    INTEGER (0..255)
ACCESS    read-write
STATUS    optional
DESCRIPTION "Indicates the low fuel level threshold used to alert the user.  The
threshold is indicated as a percent (%) of a full tank.  When the level of fuel
is below the threshold, the bit for power alarm (bit 2) in the shortErrorStatus-
object shall be set to one (1)."
::= {statPower 2}


--2.11.3.1.1.3 Fuel Level Parameter
fuelLevel OBJECT-TYPE
SYNTAX    INTEGER (0..100)
ACCESS    read-only
STATUS    optional
DESCRIPTION "A number indicating the amount of fuel remaining, specified as a
percent (%) of a full tank."
::= {statPower 3}


--2.11.3.1.1.4 Engine RPM Parameter
engineRPM OBJECT-TYPE
SYNTAX    INTEGER (0..255)
ACCESS    read-only
STATUS    optional
DESCRIPTION "Indicates the engine rpm in units of 100.  This provides a range
from 0 rpm to 25500 rpm."
::= {statPower 4}


--2.11.3.1.1.5 Line Volts Parameter
lineVolts OBJECT-TYPE
SYNTAX    INTEGER (0..255)
ACCESS    read-only
STATUS    optional
DESCRIPTION "The DMS line voltage measurement in (1.0) volts.  The range is 0
volts to 255 volts."
::= {statPower 5}


--2.11.3.1.1.6 Power Source Parameter
powerSource OBJECT-TYPE
SYNTAX    INTEGER {
                other (1),
                powerShutdown (2),
                noSignPower (3),
                acLine (4),
                generator (5),
                solar (6),
                battery (7)
                }
ACCESS    read-only
STATUS    mandatory
DESCRIPTION "Indicates the source of power that is currently utilized by the
sign."
--other: indicates that the sign is powered by a method not listed below (see
--device manual);
--powerShutdown: indicates that there is just enough power to perform shutdown
--activities.
--noSignPower: indicates that the sign controller has power but the sign display
--has no power;
--acLine: indicates that the controller and sign is powered by AC power;
--generator: indicates that the sign and the controller are powered by a
--generator;
--solar: indcates that the sign and the controller are powered by solar
--equipment;
--battery: indicates that the sign and controller are powered by battery with no
--significant charging occurring.
::= {statPower 6}


--2.11.4  Temperature Status Objects
statTemp  OBJECT IDENTIFIER ::= {dmsStatus 9}
-- This node is an identifier used to group all objects supporting DMS sign
-- temperature status monitoring functions that are common to DMS devices.


--2.11.4.1.1.1 Minimum Temperature of Control Cabinet Parameter
tempMinCtrlCabinet OBJECT-TYPE
SYNTAX    INTEGER (-128..127)
ACCESS    read-only
STATUS    optional
DESCRIPTION "Indicates the current temperature, single sensor, or the current
minimum temperature, multiple sensors, within the DMS Control Cabinet in degrees
Celsius."
::= {statTemp 1}


--2.11.4.1.1.2 Maximum Temperature of Control Cabinet Parameter
tempMaxCtrlCabinet OBJECT-TYPE
SYNTAX    INTEGER (-128..127)
ACCESS    read-only
STATUS    optional
DESCRIPTION "Indicates the current temperature, single sensor, or the current
maximum temperature, multiple sensors, within the DMS Control Cabinet in degrees
Celsius."
::= {statTemp 2}


--2.11.4.1.1.3 Minimum Ambient Temperature Parameter
tempMinAmbient OBJECT-TYPE
SYNTAX    INTEGER (-128..127)
ACCESS    read-only
STATUS    optional
DESCRIPTION "Indicates the current outside ambient temperature, single sensor,
or the current minimum outside ambient temperature, multiple sensors in degrees
Celsius."
::= {statTemp 3}


--2.11.4.1.1.4 Maximum Ambient Temperature Parameter
tempMaxAmbient OBJECT-TYPE
SYNTAX    INTEGER (-128..127)
ACCESS    read-only
STATUS    optional
DESCRIPTION "Indicates the current outside ambient temperature, single sensor,
or the current maximum outside ambient temperature, multiple sensors in degrees
Celsius."
::= {statTemp 4}


--2.11.4.1.1.5 Minimum Temperature of Sign Housing Parameter
tempMinSignHousing OBJECT-TYPE
SYNTAX    INTEGER (-128..127)
ACCESS    read-only
STATUS    optional
DESCRIPTION "Indicates the current temperature, single sensor, or the current
minimum temperature, multiple sensors in the sign housing in degrees Celsius."
::= {statTemp 5}


--2.11.4.1.1.6 Maximum Temperature of Sign Housing Parameter
tempMaxSignHousing OBJECT-TYPE
SYNTAX    INTEGER (0..255)
ACCESS    read-only
STATUS    optional
DESCRIPTION "Indicates the current temperature, single sensor, or the current
maximum temperature, multiple sensors in the sign housing in degrees Celsius."
::= {statTemp 6}

END
