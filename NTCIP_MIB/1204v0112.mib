--******************************************************************************
-- Filename:    1204v0112.MIB
-- Source:      ntcip1204v01-12.MIB
-- Description: This MIB defines the Environmental System Sensor Objects
-- Revisions:
-- 01/01/98     Preliminary Release of TS 3.7 ESS-MIB MIB formatted for 80
--              columns and no TABs
-- 01/07/98     Replaced some missed TABs with spaces
-- 07/08/98     Added Copyright Notice
-- 03/09/00     Reinstated changed due to SMIC Compiler
--              Changed filename and copyright years
--              Updated file to Proposed Amendment 1
-- 08/09/00     Modified header format and wording of copyright and MIB
--              Distribution Notice
--              Changed experimental to nemaExperimental per NTCIP 1101(SMI)
--              Amendment 
-- 03/12/01     Updated source file to that defined in NTCIP 1204 98.01.12 dated 9/28/98
--              Updated imports section to reflect MIB-II
-- 
-- 11/23/04      Filename was 1204(ESS).MIB
--                      Revised IMPORTS 
--
-- Copyright 1998-2001 by National Electrical Manufacturers Association (NEMA). 
-- All property rights, including, but not limited to, the rights of
-- reproduction, translation and display are reserved under the laws of the
-- United States of America,  the Universal Copyright Convention, the Berne
-- Convention, and the International and Pan American Copyright Conventions.
-- You may not copy these material without written permission from NEMA.
-- Use of these materials does not give you any rights of ownership or claim
-- of copyright in or to these materials.
-- To the extent that these materials are distributed by NEMA in the form of a
-- Management Information Base ("MIB"), NEMA extends the following
-- permissions:
-- (i) you may make and/or distribute unlimited copies (including derivative
-- works) of the MIB, including copies for commercial distribution, provided
-- that (a) each copy you make and/or distribute contains this Notice and (b)
-- each derivative work of the MIB uses the same module name followed by "-",
-- followed by your Internet Assigned Number Authority (IANA)-assigned
-- enterprise number;
-- (ii) use of the MIB is restricted in that the syntax field may be modified
-- only to reflect a more restrictive subrange or enumerated values;
-- (iii) the description field may be modified but only to the extent that:
-- (a) only those bit values or enumerated values that are supported are
-- listed; and (b) the more restrictive subrange is expressed.
-- These materials are delivered "AS IS" without any warranties as to their
-- use or performance.
-- NEMA AND THEIR SUPPLIERS DO NOT WARRANT THE PERFORMANCE OR RESULTS YOU MAY
-- OBTAIN BY USING THESE MATERIALS.  NEMA AND THEIR SUPPLIERS MAKE NO
-- WARRANTIES, EXPRESSED OR IMPLIED, AS TO NON-INFRINGEMENT OF THIRD PARTY
-- RIGHTS, MERCHANTABILITY, OR FITNESS FOR ANY PARTICULAR PURPOSE.  IN NO EVENT
-- WILL NEMA OR THEIR SUPPLIERS BE LIABLE TO YOU OR ANY THIRD PART FOR ANY
-- CLAIM OR FOR ANY CONSEQUENTIAL, INCIDENTAL, OR SPECIAL DAMAGES, INCLUDING
-- ANY LOST PROFITS OR LOST SAVINGS, ARISING FROM YOUR REPRODUCTION OR USE OF
-- THESE MATERIALS.  EVEN IF A NEMA REPRESENTATIVE HAS BEEN ADVISED OF THE
-- POSSIBILITY OF SUCH DAMAGES.  Some states or jurisdictions do not allow the
-- exclusion or limitation of incidental, consequential, or special damages, or
-- exclusion of implied warranties, so the above limitations may not apply to
-- you.
-- Use of these materials do not constitute an endorsement or affiliation by
-- or between NEMA and you, your company, or your products and services.
--******************************************************************************

-- 3.1 ENVIRONMENTAL SENSOR STATION (ESS) MIB HEADER INFORMATION
ESS-MIB DEFINITIONS ::= BEGIN
IMPORTS
  IpAddress, Counter
	FROM RFC1155-SMI
--    DisplayString
--                  FROM RFC1158-SMI
    OBJECT-TYPE
  	FROM RFC-1212
    DisplayString
                  FROM RFC1213-MIB
--    devices, DisplayString 
--	FROM TMIB-II;

  ess 
      FROM NTCIP8004-A-2004;
-- For the purpose of this section, the following OBJECT IDENTIFIERS are used:
-- ess OBJECT IDENTIFIER ::={devices 5}

essBufr OBJECT IDENTIFIER ::= {ess 1}
-- This node contains objects that describe BUFR information based on the BUFR 
-- Standards.

essNtcip OBJECT IDENTIFIER ::= {ess 2}
-- This node contains objects that describe surface transportation environmental 
-- information which deviate from the BUFR Standards.

-- 3.2 IDENTIFICATION OBJECTS
-- These are objects used to describe the identification of the environmental
-- sensor station. 
essNtcipIdentification  OBJECT IDENTIFIER ::= {essNtcip 1 }

-- 3.2.1 Station Category
essNtcipCategory OBJECT-TYPE
SYNTAX	INTEGER {	other (1),
			permanent (2),
			transportable (3),
			mobile (4)}
ACCESS	read-only
STATUS	mandatory
DESCRIPTION "Indicates the type of station.
value			description
other 		of a design not listed in this standard.
permanent		not designed to be relocated.
transportable	able to be relocated, but does not take readings while
			moving.
mobile		capable of taking readings while moving."
::= {essNtcipIdentification 1}

-- 3.2.2 Station Site Description
essNtcipSiteDescription OBJECT-TYPE
SYNTAX	DisplayString (SIZE (0..255))
ACCESS	read-write
STATUS	mandatory
DESCRIPTION "A textual description of the station's location."
::= {essNtcipIdentification 2}

-- it is also recognized that there would be a great value of an object to 
-- indicate the quality of data; however, this is a very complex topic and thus 
-- we have not determined an appropriate mechanism.

-- 3.3 DATA INSTRUMENTATION OBJECTS
-- Contains objects used to describe the type of data and the type of
-- instrumentation used to collect the data being received from the ess.
essBufrInstrumentation  OBJECT IDENTIFIER ::= {essBufr 2 }

-- 3.3.1 Type of Station
essTypeofStation OBJECT-TYPE
SYNTAX	INTEGER (0..3)
ACCESS	read-only
STATUS	mandatory
DESCRIPTION "Integer value that indicates the type of station.  If the station is a hybrid station, it shall be defined as two stations, one staffed and one automatic.
value			description
0 - automatic		the data is collected electronically/mechanically
1 - staffed			the data is collected by humans
3 - missingValue		the type of station is unknown."
REFERENCE "WMO Code Form FM 94 BUFR Table B item 0 02 001."
::= {essBufrInstrumentation 1}

-- The definition of the type, make, model, and version of the various sensors 
-- connected to the ESS shall be defined in the Global Module Table.

-- 3.4 LOCATION OBJECTS
-- Contains objects used to describe the location of the ess that is 
-- transmitting the collected data.

essNtcipLocation OBJECT IDENTIFIER ::= {essNtcip 2 } 

-- 3.4.1 Latitude
essLatitude OBJECT-TYPE
SYNTAX	INTEGER (-90000000..90000001)
ACCESS	read-only
STATUS	mandatory
DESCRIPTION "The latitude in 10^-6 degrees of the ESS station.  The essLatitude at the North Pole is 90,000,000.  The essLatitude at the South Pole is -90,000,000.  The value 90,000,001 shall indicate a missing value."
REFERENCE "Resolution based on on-going location referencing activities;  the WMO Code Form FM 94 BUFR Table B item 0 05 001 can be obtained by dividing this value by 10."  
::= {essNtcipLocation 1}

-- 3.4.2 Longitude
essLongitude OBJECT-TYPE
SYNTAX	INTEGER (-180000000..180000001)
ACCESS	read-only
STATUS	mandatory
DESCRIPTION "The east longitude in 10^-6 degrees from the Prime Meridian of the ESS location.  The essLongitude of 180 degrees West shall be -180,000,000.  The essLongitude of 180 degrees East shall be 180,000,000.  The value 180,000,001 shall indicate a missing value."
REFERENCE "Resolution based on on-going location referencing activities;  the WMO Code Form FM 94 BUFR Table B item 0 06 001 can be obtained by dividing this value by 10."
::= {essNtcipLocation 2}

-- 3.4.3 Vehicle Speed
essVehicleSpeed OBJECT-TYPE
SYNTAX	INTEGER (0..255)
ACCESS	read-only
STATUS	mandatory
DESCRIPTION "Indicates the current speed being reported by the vehicle in kilometers per hour.  The value 255 shall indicate an error condition or missing value."
::= { essNtcipLocation 3}

-- 3.4.4 Vehicle Bearing
essVehicleBearing OBJECT-TYPE
SYNTAX	INTEGER (0..361)
ACCESS	read-only
STATUS	mandatory
DESCRIPTION "Indicates the current bearing of the vehicle in degrees, measured clockwise from True North.  The value 361 shall indicate an error condition or missing value."
::= { essNtcipLocation 4 }

-- 3.4.5 Odometer

essOdometer OBJECT-TYPE
SYNTAX	Counter
ACCESS	read-only
STATUS	mandatory
DESCRIPTION "Indicates the current odometer reading of the vehicle in meters."
::= { essNtcipLocation 5 }

-- 3.5 STATION ELEVATION OBJECTS
-- Contains objects used to describe the elevation and atmospheric pressure at
-- the ess that is transmitting the collected data.
essNtcipHeight OBJECT IDENTIFIER ::= {essNtcip 3 }
essBufrLocationVertical OBJECT IDENTIFIER ::= {essBufr 7 }

-- 3.5.1 Reference Height
essReferenceHeight OBJECT-TYPE
SYNTAX	INTEGER (-400..8001)
ACCESS	read-only
STATUS	mandatory
DESCRIPTION "The reference elevation of the ESS in meters above mean sea level.  For a permanent station, this height shall be measured to the base of the structure; for transportable stations, this height shall be measured to the ground surface upon which the station resides; and for mobile, this height shall be measured to the surface under the vehicle.  The value 8001 shall indicate an missing value."
REFERENCE "Resolution based on WMO Code Form FM 94 BUFR Table B item 0 07 001."
::= {essNtcipHeight 1}

-- 3.5.2 Pressure Height
essPressureHeight OBJECT-TYPE
SYNTAX	INTEGER (-1000..1001)
ACCESS	read-only
STATUS	mandatory
DESCRIPTION "The height of the pressure sensor with respect to the essReferenceHeight in meters.  The value 1001 shall indicate a missing value."
REFERENCE "essRefernceHeight plus this value equals the WMO Code Form FM 94 BUFR Table B item 0 07 001."
::= {essNtcipHeight 2}

-- 3.5.3 Wind Sensor Height
essWindSensorHeight OBJECT-TYPE
SYNTAX	INTEGER (-1000..1001)
ACCESS	read-only
STATUS	mandatory
DESCRIPTION "The height of the wind sensor with respect to the essReferenceHeight in meters.  The value 1001 shall indicate a missing value."
::= {essNtcipHeight 3}

-- 3.5.4 Atmospheric Pressure Parameter
essAtmosphericPressure OBJECT-TYPE
SYNTAX	INTEGER (0..65535)
ACCESS	read-only
STATUS	mandatory
DESCRIPTION "The force per unit area exerted by the atmosphere in 1/10ths of millibars, a.k.a. tenths of hectoPascals.  A value of 65535 shall indicate an error condition or missing value."
REFERENCE "WMO Code Form FM 94 BUFR Table B item 0 07 004."
::= { essBufrLocationVertical 4}

-- 3.6 WIND DATA SECTION
-- Contains objects used to describe the wind data that is collected at the ess.
essNtcipWind OBJECT IDENTIFIER ::= {essNtcip 4 }
essBufrWind OBJECT IDENTIFIER ::= {essBufr 11 }

-- 3.6.1 Average Wind Direction
essAvgWindDirection OBJECT-TYPE
SYNTAX	INTEGER (0..361)
ACCESS	read-only
STATUS	mandatory
DESCRIPTION "A two minute average of the direction from which the wind is blowing measured clockwise in degrees from true North and measured at a height as indicated by essWindSensorHeight.  A value of 361 shall indicate an error condition or missing value."
REFERENCE "WMO Code Form FM 94 BUFR Table B item 0 11 001."
::= {essBufrWind 1}

-- 3.6.2 Average Wind Speed
essAvgWindSpeed OBJECT-TYPE
SYNTAX	INTEGER (0..65535)
ACCESS	read-only
STATUS	mandatory
DESCRIPTION "A two minute average of the wind speed in tenths of meters per second measured at a height as indicated by essWindSensorHeight.  A value of 65535 shall indicate an error condition or missing value."
REFERENCE "WMO Code Form FM 94 BUFR Table B item 0 11 002."
::= {essBufrWind 2}

-- 3.6.3 Spot Wind Direction
essSpotWindDirection OBJECT-TYPE
SYNTAX	INTEGER (0..361)
ACCESS	read-only
STATUS	mandatory
DESCRIPTION "The direction from which the wind is blowing measured in degrees clockwise from true North and measured at a height as indicated by essWindSensorHeight.  A value of 361 shall indicate an error condition or missing value.  For mobile platforms, the wind direction shall be corrected for vehicle movement."
::= { essNtcipWind 1}

-- 3.6.4 Spot Wind Speed
essSpotWindSpeed OBJECT-TYPE
SYNTAX	INTEGER (0..65535)
ACCESS	read-only
STATUS	mandatory
DESCRIPTION "The wind speed in tenths of meters per second measured at a height as indicated by essWindSensorHeight.  A value of 65535 shall indicate an error condition or missing value.  For mobile platforms, the wind speed shall be corrected for vehicle movement."
::= {essNtcipWind 2}

-- 3.6.5 Wind Situation
essWindSituation OBJECT-TYPE
SYNTAX	INTEGER { 	other (1),
		unknown (2),
		calm (3),
		lightBreeze (4),
		moderateBreeze (5),
		strongBreeze (6),
		gale (7),
		moderateGale (8),
		strongGale (9),
		stormWinds (10),
		hurricaneForceWinds (11),
		gustyWinds (12)}
ACCESS	read-only
STATUS	mandatory
DESCRIPTION "Describes the weather and travel situation in terms of wind from staffed stations only.  Specific ranges for these values are defined in the Glossary of Meteorology.  Defined values are:
	Range			Meaning
	other			not defined within this standard, consult manufacturers
				documentation
	unknown		Unknown conditions
	calm			Calm
	lightBreeze		Light breeze
	moderateBreeze	Moderate breeze
	strongBreeze	Strong breeze
	gale			Gale
	moderateGale	Moderate gale
	strongGale		Strong gale
	stormWinds		Storm winds
	hurricaneForceWinds	Hurricane force winds
	gustyWinds		Gusty winds - defined by a peak and a lull of greater 
				than 46.3 tenths of meters per second within a 2 minute 
				period."
::= {essNtcipWind 3}

-- 3.6.6 Maximum Wind Gust Speed
essMaxWindGustSpeed OBJECT-TYPE
SYNTAX	INTEGER (0..65535)
ACCESS	read-only
STATUS	mandatory
DESCRIPTION "The maximum wind gust recorded during the 10 minutes preceding the observation at a height as indicated by essWindSensorHeight and measured in tenths of meters per second.  The value 65535 shall indicate an error condition or missing value."
REFERENCE "WMO Code Form FM 94 BUFR Table B item 0 11 041."
::= {essBufrWind 41}

-- 3.6.7 Maximum Wind Gust Direction
essMaxWindGustDir OBJECT-TYPE
SYNTAX	INTEGER (0..361)
ACCESS	read-only
STATUS	mandatory
DESCRIPTION "The direction of the maximum wind gust recorded during the 10 minutes preceding the observation at a height as indicated by essWindSensorHeight; measured in degrees clockwise from true North.  The value 361 shall indicate an error condition or missing value."
REFERENCE "WMO Code Form FM 94 BUFR Table B item 0 11 043."
::= {essBufrWind 43}

-- 3.7 TEMPERATURE DATA OBJECTS
-- Contains objects used to describe the temperature data that is collected at 
-- the ess.
essNtcipTemperature OBJECT IDENTIFIER ::= {essNtcip 5 }

-- 3.7.1 Number of Temperature Sensors
essNumTemperatureSensors OBJECT-TYPE
SYNTAX	INTEGER (0..255)
ACCESS	read-only
STATUS	mandatory
DESCRIPTION "Indicates the number of entries in the temperature sensor table."
::= {essNtcipTemperature 1}

-- 3.7.2 Temperature Sensor Table
essTemperatureSensorTable OBJECT-TYPE
SYNTAX	SEQUENCE OF EssTemperatureSensorEntry
ACCESS	not-accessible
STATUS	mandatory
DESCRIPTION "Table containing the temperature sensor data fields."
::= {essNtcipTemperature 2}

essTemperatureSensorEntry OBJECT-TYPE
SYNTAX	EssTemperatureSensorEntry
ACCESS	not-accessible
STATUS	mandatory
DESCRIPTION "Parameters for specific temperature sensor data fields."
INDEX  {essTemperatureSensorIndex}
::= {essTemperatureSensorTable 1}

EssTemperatureSensorEntry ::= SEQUENCE {
	essTemperatureSensorIndex		INTEGER,
	essTemperatureSensorHeight		INTEGER,
	essAirTemperature				INTEGER }

-- 3.7.2.1 Temperature Sensor Index
essTemperatureSensorIndex OBJECT-TYPE
SYNTAX	INTEGER (1..255)
ACCESS	read-only
STATUS	mandatory
DESCRIPTION "Enumerated list of row entries that will provide temperature sensor data."
::= {essTemperatureSensorEntry 1}

-- 3.7.2.2 Temperature Sensor Height
essTemperatureSensorHeight OBJECT-TYPE
SYNTAX	INTEGER (-1000..1001)
ACCESS	read-only
STATUS	mandatory
DESCRIPTION "The height of the temperature sensor as measured in meters above essReferenceHeight."
::= { essTemperatureSensorEntry 2}

-- 3.7.2.3 Air Temperature
essAirTemperature OBJECT-TYPE
SYNTAX	INTEGER (-1000..1001)
ACCESS	read-only
STATUS	mandatory
DESCRIPTION "The dry-bulb temperature in tenths of degrees Celsius.  The temperature is an instantaneous reading  at the height specified by essTemperatureSensorHeight.  The value 1001 shall indicate an error condition or missing value."
REFERENCE "Resolution is based on WMO Code Form FM 94 BUFR Table B item 0 12 001; temperature in kelvin is determined by adding 273.15 to this value."
::= { essTemperatureSensorEntry 3}

-- 3.7.3 Wet-Bulb Temperature
essWetbulbTemp OBJECT-TYPE
SYNTAX	INTEGER (-1000..1001)
ACCESS	read-only
STATUS	mandatory
DESCRIPTION "The wet-bulb temperature in tenths of degrees Celsius.  The temperature is an instantaneous reading at the height specified by the essTemperatureSensorHeight as specified in the first row of the essTemperatureTable.  The value 1001 shall indicate an error condition or missing value."
REFERENCE "Resolution is based on WMO Code Form FM 94 BUFR Table B item 0 12 002; temperature in kelvin is determined by adding 273.15 to this value."
::= {essNtcipTemperature 3}

-- 3.7.4 Dew-Point Temperature
essDewpointTemp OBJECT-TYPE
SYNTAX	INTEGER (-1000..1001)
ACCESS	read-only
STATUS	mandatory
DESCRIPTION "The dewpoint temperature in tenths of degrees Celsius.  The temperature is an instantaneous reading at the height specified by the essTemperatureSensorHeight as specified in the first row of the essTemperatureTable.  The value 1001 shall indicate an error condition or missing value."
REFERENCE "Resolution is based on WMO Code Form FM 94 BUFR Table B item 0 12 003; temperature in kelvin is determined by adding 273.15 to this value."
::= {essNtcipTemperature 4}

-- 3.7.5 Maximum Temperature
essMaxTemp OBJECT-TYPE
SYNTAX	INTEGER (-1000..1001)
ACCESS	read-only
STATUS	mandatory
DESCRIPTION "The maximum temperature in tenths of degrees Celsius recorded during the 24 hours preceding the observation at the height specified by the essTemperatureSensorHeight as specified in the first row of the essTemperatureTable.  The value 1001 shall indicate an error condition or missing value."
REFERENCE "Resolution is based on WMO Code Form FM 94 BUFR Table B item 0 12 011; temperature in kelvin is determined by adding 273.15 to this value."
::= {essNtcipTemperature 5}

-- 3.7.6 Minimum Temperature
essMinTemp OBJECT-TYPE
SYNTAX	INTEGER (-1000..1001)
ACCESS	read-only
STATUS	mandatory
DESCRIPTION "The minimum temperature in tenths of degrees Celsius recorded during the 24 hours preceding the observation at the height specified by the essTemperatureSensorHeight as specified in the first row of the essTemperatureTable.  The value 1001 shall indicate an error condition or missing value."
REFERENCE "Resolution is based on WMO Code Form FM 94 BUFR Table B item 0 12 012; temperature in kelvin is determined by adding 273.15 to this value."
::= {essNtcipTemperature 6}

-- 3.8 HUMIDITY AND PRECIPITATION DATA OBJECTS
-- Contains objects used to describe the humidity and precipitation data that is 
-- collected by the ess.
essBufrPrecip OBJECT IDENTIFIER ::= {essBufr 13 }
essNtcipPrecip OBJECT IDENTIFIER ::= {essNtcip 6 }

-- 3.8.1 Relative Humidity
essRelativeHumidity OBJECT-TYPE
SYNTAX	INTEGER (0..101)
ACCESS	read-only
STATUS	mandatory
DESCRIPTION "The relative humidity in percent.  The value of 101 shall indicate an error condition or missing value."
REFERENCE "WMO Code Form FM 94 BUFR Table B item 0 13 003."
::= {essBufrPrecip 3}

-- 3.8.2 Water Depth
essWaterDepth OBJECT-TYPE
SYNTAX	INTEGER (0..65535)
ACCESS	read-only
STATUS	optional
DESCRIPTION "Indicates the depth of the water from a user defined point in centimeters.  The value of 65535 shall indicate an error condition or missing value.  This may be used for stream depth, depth of water over a roadway, reservoir depth, or other such uses."
::= {essNtcipPrecip 1}

-- 3.8.3 Adjacent Snow Depth
essAdjacentSnowDepth OBJECT-TYPE
SYNTAX	INTEGER (0..3001)
ACCESS	read-only
STATUS	mandatory
DESCRIPTION "The depth of snow in centimeters on representative areas other than the highway pavement, avoiding drifts and plowed areas.  The value 3001 shall indicate an error condition or missing value."
::={ essNtcipPrecip 2}

-- 3.8.4 Roadway Snow Depth
essRoadwaySnowDepth OBJECT-TYPE
SYNTAX   INTEGER (0..3001)
ACCESS   read-only
STATUS   mandatory
DESCRIPTION "The current depth of unpacked snow in centimeters on the driving surface.  The value 3001 shall indicate an error condition or missing value."
::={essNtcipPrecip 3}

-- 3.8.5 Roadway Snow Pack Depth
essRoadwaySnowPackDepth OBJECT-TYPE
SYNTAX	INTEGER (0..3001)
ACCESS	read-only
STATUS	mandatory
DESCRIPTION "The current depth of packed snow in centimeters on the roadway surface.  The value 3001 shall indicate an error condition or missing value."
::={ essNtcipPrecip 4}

-- 3.8.6 Precipitation Indicator
essPrecipYesNo OBJECT-TYPE
SYNTAX   INTEGER {	precip (1),
			noPrecip (2),
			error (3)}
ACCESS   read-only
STATUS   mandatory
DESCRIPTION "Indicates whether or not moisture is detected by the sensor."
::={ essNtcipPrecip 5}

-- 3.8.7 Rainfall or Water Equivalent of Snow
essPrecipRate OBJECT-TYPE
SYNTAX	INTEGER (0..65535)
ACCESS	read-only
STATUS	mandatory
DESCRIPTION "The rainfall, or water equivalent of snow, rate in tenths of grams per square meter per second (for rain, this is approximately  to 0.36 mm/hr).  A value of 65535 shall indicate an error condition or missing value."
REFERENCE "WMO Code Form FM 94 BUFR Table B item 0 13 014."
::= { essBufrPrecip 14}

-- 3.8.8 Snowfall Accumulation Rate
essSnowfallAccumRate OBJECT-TYPE
SYNTAX	INTEGER (0..65535)
ACCESS	read-only
STATUS	mandatory
DESCRIPTION "The snowfall accumulation rate in 10^-7 meters per second (this is equivalent to 0.36 mm/hr).  The value 65535 shall indicate an error condition or missing value."
REFERENCE "WMO Code Form FM 94 BUFR Table B item 0 13 015."
::= { essBufrPrecip 15}

-- 3.8.9 Precipitation Situation
essPrecipSituation OBJECT-TYPE
SYNTAX	INTEGER {	other (1),
		unknown (2),
		noPrecipitation (3),
		unidentifiedSlight (4),
		unidentifiedModerate (5),
		unidentifiedHeavy (6),
		snowSlight (7),
		snowModerate (8),
		snowHeavy (9),
		rainSlight (10),
		rainModerate (11),
		rainHeavy (12),
		frozenPrecipitationSlight (13),
		frozenPrecipitationModerate (14),
		frozenPrecipitationHeavy (15)}
ACCESS	read-only
STATUS	mandatory
DESCRIPTION "Describes the weather situation in terms of precipitation.  Defined values of intensity are:
	Intensity					Meaning
	slight						< 2mm/h water equivalent
	moderate					>= 2 and < 8 mm/h water equivalent
	heavy						>= 8 mm/h water equivalent
If one exists, the corresponding BUFR value is indicated for staffed (BUFRs) and automated (BUFRa) stations.  The indicated value can be found in the BUFR Table referenced below.  Defined values are:
	Range		BUFRa		BUFRs		Meaning
	1						other
	2						unknown	
	3						no precipitation
4						unidentified slight
	5						unidentified moderate
	6						unidentified heavy
	7		171		85		snow slight
	8		172		86		snow moderate
	9		173		86		snow heavy
	10				61		rain slight
	11		165		63		rain moderate
	12		163		65		rain heavy
	13						frozen precipitation slight
	14						frozen precipitation moderate
	15						frozen precipitation heavy"
REFERENCE "The values identified in the above table for BUFRa and BUFRs can be found in WMO Code Form FM 94 BUFR Table B item 0 20 003."
::= { essNtcipPrecip 6}

-- 3.8.10 Ice Deposit (Thickness)
essIceThickness OBJECT-TYPE
SYNTAX	INTEGER (0..65535)
ACCESS	read-only
STATUS	optional
DESCRIPTION "Indicates the thickness of the ice in millimeters.  The value 65535 shall indicate an error condition or missing value."
::= {essNtcipPrecip 7}

-- 3.8.11 Precipitation Start Time
essPrecipitationStartTime OBJECT-TYPE
SYNTAX	INTEGER (0..4294967295)
ACCESS	read-only
STATUS	mandatory
DESCRIPTION "The time at which the most recent precipitation event began, measured in seconds since 00:00:00 January 1, 1970 UTC.  As this standard has been developed long after 1970, a value of 0 for the time should indicate to the management station that the data received is suspect."
::= { essNtcipPrecip 8}

-- 3.8.12 Precipitation End Time
essPrecipitationEndTime OBJECT-TYPE
SYNTAX	INTEGER (0..4294967295)
ACCESS	read-only
STATUS	mandatory
DESCRIPTION "The time at which the most recently completed precipitation event ended, measured in seconds since 00:00:00 January 1, 1970 UTC.  As this standard has been developed long after 1970, a value of 0 for the time should indicate to the management station that the data received is suspect."
::= { essNtcipPrecip 9}

-- 3.8.13 Total Precipitation Past One Hour
essPrecipitationOneHour OBJECT-TYPE
SYNTAX	INTEGER (0..65535)
ACCESS	read-only
STATUS	mandatory
DESCRIPTION "The total water equivalent precipitation over the hour preceding the observation in tenths of kilograms per square meter (for rain, this is approximately tenths of  millimeters).  A value of 65535 shall indicate an error condition or missing value."
REFERENCE "WMO Code Form FM 94 BUFR Table B item 0 13 019."
::= { essBufrPrecip 19}

-- 3.8.14 Total Precipitation Past Three Hours
essPrecipitationThreeHours OBJECT-TYPE
SYNTAX	INTEGER (0..65535)
ACCESS	read-only
STATUS	mandatory
DESCRIPTION "The total water equivalent precipitation over the three hours preceding the observation in tenths of kilograms per square meter (for rain, this is approximately tenths of  millimeters).  A value of 65535 shall indicate an error condition or missing value."
REFERENCE "WMO Code Form FM 94 BUFR Table B item 0 13 020."
::= { essBufrPrecip 20}

-- 3.8.15 Total Precipitation Past Six Hours
essPrecipitationSixHours OBJECT-TYPE
SYNTAX	INTEGER (0..65535)
ACCESS	read-only
STATUS	mandatory
DESCRIPTION "The total water equivalent precipitation over the six hours preceding the observation in tenths of kilograms per square meter (for rain, this is approximately tenths of  millimeters).  A value of 65535 shall indicate an error condition or missing value."
REFERENCE "WMO Code Form FM 94 BUFR Table B item 0 13 021."
::= { essBufrPrecip 21}

-- 3.8.16 Total Precipitation Past Twelve Hours
essPrecipitationTwelveHours OBJECT-TYPE
SYNTAX	INTEGER (0..65535)
ACCESS	read-only
STATUS	mandatory
DESCRIPTION "The total water equivalent precipitation over the twelve hours preceding the observation in tenths of kilograms per square meter (for rain, this is approximately to tenths of  millimeters).  A value of 65535 shall indicate an error condition or missing value."
REFERENCE "WMO Code Form FM 94 BUFR Table B item 0 13 022."
::= { essBufrPrecip 22}

-- 3.8.17 Total Precipitation Past Twenty-Four Hours
essPrecipitation24Hours OBJECT-TYPE
SYNTAX	INTEGER (0..65535)
ACCESS	read-only
STATUS	mandatory
DESCRIPTION "The total water equivalent precipitation over the twenty-four hours preceding the observation in tenths of kilograms per square meter (for rain, this is equivalent to tenths of  millimeters).  A value of 65535 shall indicate an error condition or missing value."
REFERENCE "WMO Code Form FM 94 BUFR Table B item 0 13 023."
::= { essBufrPrecip 23}

-- 3.9 RADIATION OBJECTS
-- Contains objects used to describe the data that is collected by the pavement 
-- surface sensor.
essBufrRadiation  OBJECT IDENTIFIER ::= {essBufr 14 }
essNtcipRadiation  OBJECT IDENTIFIER ::= {essNtcip 7}

-- 3.9.1.1 Solar Radiation
essSolarRadiation OBJECT-TYPE
SYNTAX	INTEGER (0..65535)
ACCESS	read-only
STATUS	mandatory
DESCRIPTION "The direct solar radiation integrated over the 24 hours preceding the observation in Joules per square meter.  A value of 65535 shall indicate a missing value."
REFERENCE "WMO Code Form FM 94 BUFR Table B item 0 14 024."
::= {essBufrRadiation 24}

-- 3.9.1.2 Total Sun
essTotalSun OBJECT-TYPE
SYNTAX	INTEGER (0..1441)
ACCESS	read-only
STATUS	mandatory
DESCRIPTION "The total amount of sunshine in minutes over the 24 hour period preceding the observation.  A value of 1441 shall indicate a missing value."
REFERENCE "WMO Code Form FM 94 BUFR Table B item 0 14 031."
::= {essBufrRadiation 31}

-- 3.9.2 Cloud Cover Situation
essCloudSituation OBJECT-TYPE
SYNTAX	INTEGER {	overcast (1),
		cloudy (2),
		partlyCloudy (3),
		mostlyClear (4),
		clear (5)}
ACCESS	read-only
STATUS	mandatory
DESCRIPTION "Describes the amount of cloud cover.  The associated percentages of cloud cover are indicated to identify the differences between the defined values.  Defined values are:
	Value			Meaning		Percent Cloud Cover
	1			Overcast		100 %
	2			Mostly cloudy 	62.5 % - 99 %
	3			Partly cloudy 	37.5 % - 62.4 %
	4			Mostly sunny	1 % - 37.4 %
	5			Clear skies		0 %"
::= {essNtcipRadiation 1}

-- 3.10 VISIBILITY DATA OBJECTS
-- Contains objects used to describe the visibility data that is collected by 
-- the ess.
essNtcipVisibility  OBJECT IDENTIFIER ::= {essNtcip 8 }

-- 3.10.1 Visibility Parameter
essVisibility OBJECT-TYPE
SYNTAX	INTEGER (0..1000001)
ACCESS	read-only
STATUS	mandatory
DESCRIPTION "Surface visibility measured in one tenth of a meter.  The value 1000001 shall indicate an error condition or missing value."
REFERENCE "The value for WMO Code Form FM 94 BUFR Table B item 0 20 001 is given by this value divided by 100."
::= { essNtcipVisibility 1}

-- 3.10.2 Visibility Situation
essVisibilitySituation OBJECT-TYPE
SYNTAX	INTEGER {	other (1),
		unknown (2),
		clear (3),
		fogNotPatchy (4),
		patchyFog (5),
		blowingSnow (6),
		smoke (7),
		seaSpray (8),
		vehicleSpray (9),
		blowingDustOrSand (10),
		sunGlare (11),
		swarmsOfInsects (12)}
ACCESS	read-only
STATUS	mandatory
DESCRIPTION "Describes the travel environment in terms of visibility.  If one exists, the corresponding BUFR value is indicated for staffed (BUFRs) and automated (BUFRa) stations.  The indicated value can be found in the BUFR Table referenced below.  Defined values are:
	Range		BUFRs		BUFRa		Meaning
	1						other visibility anomaly
	2						unknown
	3		0		100		clear
	4		44		130		Fog - not patchy
	5		41		131		Patchy fog
	6		36		127		Blowing snow
	7		04		104		Smoke
	8		07		207		Sea Spray
	9						Vehicle Spray
	10		31		127		Blowing dust or sand
	11						sun glare
12						Swarms of insects"
REFERENCE "The values identified in the above table for BUFRa and BUFRs can be found in WMO Code Form FM 94 BUFR Table B item 0 20 003."
::= {essNtcipVisibility 3}

-- 3.11 PAVEMENT SENSOR OBJECTS
-- Contains objects used to describe the data that is collected by the pavement 
-- surface sensor.
essNtcipPavement  OBJECT IDENTIFIER ::= {essNtcip 9}

-- 3.11.1 Number of Pavement Sensors
numEssPavementSensors OBJECT-TYPE
SYNTAX	INTEGER (0..255)
ACCESS	read-only
STATUS	mandatory
DESCRIPTION "Indicates the number of entries in the pavement sensor table."
::= {essNtcipPavement 1}

-- 3.11.2 Pavement Sensor Table
essPavementSensorTable OBJECT-TYPE
SYNTAX	SEQUENCE OF EssPavementSensorEntry
ACCESS	not-accessible
STATUS	mandatory
DESCRIPTION "Table containing the pavement sensor data fields."
::= {essNtcipPavement 2}

essPavementSensorEntry OBJECT-TYPE
SYNTAX	EssPavementSensorEntry
ACCESS	not-accessible
STATUS	mandatory
DESCRIPTION "Parameters for specific pavement sensor data fields."
INDEX  {essPavementSensorIndex}
::= {essPavementSensorTable 1}

EssPavementSensorEntry ::= SEQUENCE {
	essPavementSensorIndex			INTEGER,
	essPavementSensorLocation		DisplayString,
	essPavementType				INTEGER,
	essPavementElevation			INTEGER,
	essPavementExposure			INTEGER,
	essPavementSensorType			INTEGER,
	essSurfaceStatus				INTEGER,
	essSurfaceTemperature			INTEGER,
	essPavementTemperature			INTEGER,
	essSurfaceWaterDepth			INTEGER,
	essSurfaceSalinity 			INTEGER,
	essSurfaceConductivity			INTEGER,
	essSurfaceFreezePoint			INTEGER,
	essSurfaceBlackIceSignal		INTEGER,
	essPavementSensorError			INTEGER}

-- 3.11.2.1 Pavement Sensor Index
essPavementSensorIndex OBJECT-TYPE
SYNTAX	INTEGER (1..255)
ACCESS	read-only
STATUS	mandatory
DESCRIPTION "Enumerated list of row entries that will provide surface sensor data."
::= {essPavementSensorEntry 1}

-- 3.11.2.2 Pavement Sensor Location
essPavementSensorLocation OBJECT-TYPE
SYNTAX	DisplayString (SIZE (0..255))
ACCESS	read-write
STATUS	mandatory
DESCRIPTION "A textual string indicating the location of the pavement sensor."
::= { essPavementSensorEntry 2}

-- We have contacted the LRMS group to express a need for a better mechanism for 
-- defining this location down to the lane level.

-- 3.11.2.3 Pavement Type
essPavementType OBJECT-TYPE
SYNTAX	INTEGER {	other (1),
		unknown (2),
		asphalt (3),
		openGradedAsphalt (4),
		concrete (5),
		steelBridge (6),
		concreteBridge (7),
		asphaltOverlayBridge (8),
		timberBridge (9) }
ACCESS	read-write
STATUS	mandatory
DESCRIPTION "Indicates the type of pavement on the roadway.
other	 		a different type of bridge deck
unknown 		the data was never recorded in the system
asphalt 		asphalt pavement on ground
concrete 		concrete pavement on ground
steelBridgeconcrete 	a concrete driving surface on a steel girder bridge
steelBridgeAsphalt	an asphalt driving surface on a steel girder bridge
steelBridge		a steel lattice driving surface on the bridge
concreteBridge 		a concrete driving surface on a concrete bridge
concreteBridgeAsphalt	an asphalt overlay driving surface on a concrete bridge
timberBridge		a wooden deck driving surface on the bridge"
::= { essPavementSensorEntry 3}

-- 3.11.2.4 Pavement Elevation
essPavementElevation OBJECT-TYPE
SYNTAX	INTEGER (-1000..1001)
ACCESS	read-only
STATUS	mandatory
DESCRIPTION "The elevation of the street surface in meters with respect to the essReferenceHeight.  The value 1001 shall indicate a missing value."
::= { essPavementSensorEntry 4}

-- 3.11.2.5 Pavement Exposure
essPavementExposure OBJECT-TYPE
SYNTAX	INTEGER (0..101)
ACCESS	read-write
STATUS	mandatory
DESCRIPTION "Indicates a very rough percentage of the solar energy which will directly hit the sensor.  A value of 100 indicates a fully visible sky.  A value of 101 shall indicate a missing value."
::= { essPavementSensorEntry 5}

-- 3.11.2.6 Pavement Sensor Type
essPavementSensorType OBJECT-TYPE
SYNTAX	INTEGER {other (1),
		contactPassive (2),
		contactActive (3),
		infrared (4),
		radar (5),
		vibrating (6),
		microwave (7)}
ACCESS	read-only
STATUS	mandatory
DESCRIPTION "A value indicating the type of pavement sensor."
::= { essPavementSensorEntry 6}

-- 3.11.2.7 Surface Status
essSurfaceStatus OBJECT-TYPE
SYNTAX	INTEGER {	other (1),
		error (2),
		dry (3),
		traceMoisture (4),
		wet (5),
		chemicallyWet (6),
		iceWarning (7),
		iceWatch (8),
		snowWarning (9),
		snowWatch (10),
		absorption (11),
		dew (12),
		frost (13),
		absorptionAtDewpoint (14) }
ACCESS	read-only
STATUS	mandatory
DESCRIPTION "A value indicating the pavement surface status."
::= { essPavementSensorEntry 7}

-- 3.11.2.8 Surface Temperature
essSurfaceTemperature OBJECT-TYPE
SYNTAX	INTEGER (-1000..1001)
ACCESS	read-only
STATUS	mandatory
DESCRIPTION "The current pavement surface temperature in tenths of degrees Celsius.  The value 1001 shall indicate an error condition or missing value."
::= { essPavementSensorEntry 8}

-- 3.11.2.9 Pavement Temperature
essPavementTemperature OBJECT-TYPE
SYNTAX	INTEGER (-1000..1001)
ACCESS	read-only
STATUS	optional
DESCRIPTION "The current pavement temperature 2-10 cm below the pavement surface in tenths of degrees Celsius.  The value 1001 shall indicate an error condition or missing value."
::= { essPavementSensorEntry 9}

-- 3.11.2.10 Surface Water Depth
essSurfaceWaterDepth OBJECT-TYPE
SYNTAX	INTEGER (0..255)
ACCESS	read-only
STATUS	optional
DESCRIPTION "The current depth of water on the surface of the roadway measured in millimeters.  The value 255 shall indicate an error condition or missing value."
::= { essPavementSensorEntry 10}

-- 3.11.2.11 Surface Salinity
essSurfaceSalinity OBJECT-TYPE
SYNTAX	INTEGER (0..65535) 
ACCESS	read-only
STATUS	optional
DESCRIPTION "The pavement salinity in parts per one hundred thousand.  The value 65535 shall indicate an error condition or missing value."
::= { essPavementSensorEntry 11}

-- 3.11.2.12 Surface Conductivity
essSurfaceConductivity OBJECT-TYPE
SYNTAX	INTEGER (0..65535) 
ACCESS	read-only
STATUS	optional
DESCRIPTION "Indicates the conductance of the ice/liquid mixture on the pavement as detected by the sensor, in mhos, which is the inverse of ohms. The value  65535 shall indicate an error condition or missing value."
::= { essPavementSensorEntry 12}

-- 3.11.2.13 Pavement Freezing Point
essSurfaceFreezePoint OBJECT-TYPE
SYNTAX	INTEGER (-1000..1001)
ACCESS	read-only
STATUS	optional
DESCRIPTION "The temperature in tenths of degrees Celsius at which the existing solution on the roadway will freeze.  The value 1001 shall indicate an error condition or missing value."
::= { essPavementSensorEntry 13}

-- 3.11.2.14 Surface Black Ice Signal
essSurfaceBlackIceSignal OBJECT-TYPE
SYNTAX	INTEGER {other (1),
		noIce (2),
		blackIce (3),
		detectorError (4) }
ACCESS	read-only
STATUS	optional
DESCRIPTION "A value indicating if Black Ice is detected by the sensor."
::= { essPavementSensorEntry 14}

-- 3.11.2.15 Surface Sensor Error
essPavementSensorError OBJECT-TYPE
SYNTAX	INTEGER {other (1),
		none (2),
		noResponse (3),
		cutCable (4),
		shortCircuit (5),
		dirtyLens (6) }
ACCESS	read-only
STATUS	mandatory
DESCRIPTION "A value indicating the type of pavement sensor error."
::= { essPavementSensorEntry 15}

-- 3.11.3 Number of Sub-Surface Sensors
numEssSubSurfaceSensors OBJECT-TYPE
SYNTAX	INTEGER (0..255)
ACCESS	read-only
STATUS	mandatory
DESCRIPTION "Indicates the number of entries in the Sub-Surface Sensor Table."
::= {essNtcipPavement 3}

-- 3.11.4 Sub-Surface Sensor Table
essSubSurfaceSensorTable OBJECT-TYPE
SYNTAX	SEQUENCE OF EssSubSurfaceSensorEntry
ACCESS	not-accessible
STATUS	mandatory
DESCRIPTION "Table containing the surface sensor data fields."
::= {essNtcipPavement 4}

essSubSurfaceSensorEntry OBJECT-TYPE
SYNTAX	EssSubSurfaceSensorEntry
ACCESS	not-accessible
STATUS	mandatory
DESCRIPTION "Parameters for specific sub-surface sensor data fields."
INDEX  {essSubSurfaceSensorIndex}
::= {essSubSurfaceSensorTable 1}

EssSubSurfaceSensorEntry ::= SEQUENCE {
	essSubSurfaceSensorIndex			INTEGER,
	essSubSurfaceSensorLocation			DisplayString,
	essSubSurfaceType				INTEGER,
	essSubSurfaceSensorDepth			INTEGER,
	essSubSurfaceTemperature			INTEGER,
	essSubSurfaceMoisture				INTEGER,
	essSubSurfaceSensorError			INTEGER}

-- 3.11.4.1 Sub-Surface Sensor Index
essSubSurfaceSensorIndex OBJECT-TYPE
SYNTAX	INTEGER (1..255)
ACCESS	read-only
STATUS	mandatory
DESCRIPTION "Enumerated list of row entries that will provide surface sensor data."
::= { essSubSurfaceSensorEntry 1}

-- 3.11.4.2 Sub-Surface Sensor Location
essSubSurfaceSensorLocation OBJECT-TYPE
SYNTAX	DisplayString (SIZE (0..255))
ACCESS	read-write
STATUS	mandatory
DESCRIPTION "A textual string indicating the location of the subsurface sensor."
::= { essSubSurfaceSensorEntry 2}

-- 3.11.4.3 Sub-Surface Type
essSubSurfaceType OBJECT-TYPE
SYNTAX	INTEGER {other (1),
		unknown (2),
		concrete (3),
		asphalt (4),
		openGradedAsphalt (5),
		gravel (6),
		clay (7),
		loam (8),
		sand (9),
		permafrost (10),
		variousAggregates (11),
		air (12)}
ACCESS	read-write
STATUS	mandatory
DESCRIPTION "Indicates the type of sub-surface.  A value of air would indicate a bridge."
::= { essSubSurfaceSensorEntry 3}

-- 3.11.4.4 Sub-Surface Sensor Depth
essSubSurfaceSensorDepth OBJECT-TYPE
SYNTAX	INTEGER (0..1001)
ACCESS	read-write
STATUS	mandatory
DESCRIPTION "Depth of sub-surface sensor in centimeters below the pavement surface.  The value 1001 shall indicate an error condition or missing value."
::= { essSubSurfaceSensorEntry 4}

-- 3.11.4.5 Sub-Surface Temperature
essSubSurfaceTemperature OBJECT-TYPE
SYNTAX	INTEGER (-1000..1001)
ACCESS	read-only
STATUS	mandatory
DESCRIPTION "The current sub-surface temperature in tenths of degrees Celsius.  The value 1001 shall indicate an error condition or missing value."
::= { essSubSurfaceSensorEntry 5}

-- 3.11.4.6 Sub-Surface Moisture
essSubSurfaceMoisture OBJECT-TYPE
SYNTAX	INTEGER (0..101)
ACCESS	read-only
STATUS	optional
DESCRIPTION "The sub-surface moisture expressed as a percentage (eg. 0 indicates dry, 100 indicates saturated).  The value 101 indicates an error condition or missing value"
::= { essSubSurfaceSensorEntry 7}

-- 3.11.4.7 Sub-Surface Sensor Error
essSubSurfaceSensorError OBJECT-TYPE
SYNTAX	INTEGER {other (1),
		none (2),
		noResponse (3),
		cutCable (4),
		shortCircuit (5)}
ACCESS	read-only
STATUS	mandatory
DESCRIPTION "A value indicating the type of sensor error."
::= { essSubSurfaceSensorEntry 8}

-- 3.12 MOBILE PLATFORM OBJECTS
-- This node contains objects which have been developed to facilitate 
-- experiments with data that collected by mobile platforms (e.g., specially-
-- equipped maintenance vehicles).  There has been limited use of mobile ESS 
-- platforms within the surface transportation industry and as 
-- such these objects should be considered experimental.
-- It is expected that mobile platforms will use the objects defined above plus 
-- these objects.
essNtcipMobile  OBJECT IDENTIFIER ::= {essNtcip 10}

-- 3.12.1 Mobile Friction
essMobileFriction OBJECT-TYPE
SYNTAX	INTEGER (0..101)
ACCESS	read-only
STATUS	mandatory
DESCRIPTION "Indicates measured coefficient of friction in percent.  The value 101 shall indicate an error condition or missing value."
::= { essNtcipMobile 1}

-- 3.12.2 Mobile Observation for the State of the Ground
essMobileObservationGroundState OBJECT-TYPE
SYNTAX	INTEGER {other (1),
		dry (2),
		moist (3),
		wet (4),
		flooded (5),
		frozen (6),
		glaze (7),
		dustySandy (8),
		veryDry (9),
		icy (10),
		patchyWetSnow (11),
		moderateWetSnowCover (12),
		fullWetSnowCover (13),
		patchyDrySnow (14),
		moderateDrySnowCover (15),
		fullDrySnowCover (16),
		driftingSnow (17),
		unknown (18)}
ACCESS	read-only
STATUS	mandatory
DESCRIPTION "The prevailing observed ground state of the surrounding environment as determined by the observer.  This is an indicator of past weather conditions."
::= { essNtcipMobile 2}

-- 3.12.3 Mobile State of the Pavement
essMobileObservationPavement OBJECT-TYPE
SYNTAX	INTEGER {other (1),
		dry (2),
		wet (3),
		puddles (4),
		shallowStandingWater (5),
		shallowFlowingWater (6),
		deepStandingWater (7),
		deepFlowingWater (8),
		dustingFreshSnow (9),
		moderateFreshSnow (10),
		deepFreshSnow (11),
		plowedSnow (12),
		slush (13),
		packedSnowPatches (14),
		packedSnow (15),
		lightSnowDrifts (16),
		moderateSnowDrifts (17),
		heavySnowDrifts (18),
		frost (19),
		icePatches (20),
		moderatelyIcy (21),
		heavyIcing (22),
		blackIce (23),
		sheetIce (24),
		frozenSlush (25) }
ACCESS	read-only
STATUS	mandatory
DESCRIPTION "The prevailing observed conditions on the driving surface as determined by the observer."
::= { essNtcipMobile 3}

-- 3.13 PAVEMENT TREATMENT OBJECTS
-- This node contains objects which have been developed to monitor the various 
-- types and amounts of treatments that are spread on the pavement surface.
essNtcipTreatment OBJECT IDENTIFIER ::= { essNtcip 11 }

-- 3.13.1 Number of Treatments
numEssTreatments OBJECT-TYPE
SYNTAX	INTEGER (0..255)
ACCESS	read-only
STATUS	mandatory
DESCRIPTION "Indicates the number of entries in the Pavement Treatment Table."
::= {essNtcipTreatment 1}

-- 3.13.2 Pavement Treatment Table
essPavementTreatmentTable OBJECT-TYPE
SYNTAX	SEQUENCE OF EssPavementTreatmentEntry
ACCESS	not-accessible
STATUS	mandatory
DESCRIPTION "Table containing the pavement treatment data fields."
::= {essNtcipTreatment 2}

essPavementTreatmentEntry OBJECT-TYPE
SYNTAX	EssPavementTreatmentEntry
ACCESS	not-accessible
STATUS	mandatory
DESCRIPTION "Parameters for specific pavement treatment data fields."
INDEX  {essPavementTreatmentIndex}
::= {essPavementTreatmentTable 1}

EssPavementTreatmentEntry ::= SEQUENCE {
	essPavementTreatmentIndex			INTEGER,
	essPaveTreatProductType			INTEGER,
	essPaveTreatProductForm			INTEGER,
	essPercentProductMix				INTEGER}

-- 3.13.2.1 Pavement Treatment Index
essPavementTreatmentIndex OBJECT-TYPE
SYNTAX	INTEGER (1..255)
ACCESS	read-only
STATUS	mandatory
DESCRIPTION "Enumerated list of row entries that will provide pavement treatment data."
::= { essPavementTreatmentEntry 1}

-- 3.13.2.2 Pavement Treatment Product Type
essPaveTreatProductType OBJECT-TYPE
SYNTAX	INTEGER {other (1),
		sand (2),
		dirt (3),
		gravel (4),
		cinders (5),
		water (6),
		enhancedSalts (7),
		naCl (8),
		caCl (9),
		mgCl (10),
		cMA (11),
		kAC (12),
		naFormate (13),
		naA (14) }
ACCESS	read-only
STATUS	mandatory
DESCRIPTION "Indicates the type of treatment being applied to the road.  An enhanced definition of some of the values are as follows:
other - any other type of treatment
water - used as a diluting agent
cMA - Calcium-Magnesium Acetate
kAC - Potassium-Magnesium Acetate
naFormate - Sodium Formate
naA - Sodium Acetate"
::= { essPavementTreatmentEntry 2}

-- 3.13.2.3 Treatment Product Form
essPaveTreatProductForm OBJECT-TYPE
SYNTAX	INTEGER {	other (1),
		dry (2),
		prewet (3),
		liquid (4)}
ACCESS	read-only
STATUS	mandatory
DESCRIPTION "Indicates the condition of the treatment being applied to the road."
::= { essPavementTreatmentEntry 3}

-- 3.13.2.4 Percentage of Treatment Type in Mix
essPercentProductMix OBJECT-TYPE
SYNTAX	INTEGER (0..100)
ACCESS	read-only
STATUS	mandatory
DESCRIPTION "Indicates the percentage of the total application mix by weight that is of the type specified in essPaveTreatProductType.  The sum of these percentages within the total mixture shall equal 100."
::= { essPavementTreatmentEntry 4}

-- 3.13.3 Treatment Amount
essPaveTreatmentAmount OBJECT-TYPE
SYNTAX	INTEGER (0..255)
ACCESS	read-only
STATUS	mandatory
DESCRIPTION "Indicates quantity of the treatment being applied in kilograms per lane kilometer."
::= { essNtcipTreatment 3}

-- 3.13.4 Treatment Width
essPaveTreatmentWidth OBJECT-TYPE
SYNTAX	INTEGER (0..255)
ACCESS	read-only
STATUS	mandatory
DESCRIPTION "Indicates the width of the spread of treatment in meters."
::= { essNtcipTreatment 4}

-- 3.14 AIR QUALITY PARAMETERS
essNtcipAirQuality  OBJECT IDENTIFIER ::= { essNtcip 12 }
-- This node contains objects used for monitoring air quality conditions. 

-- 3.14.1 Carbon Monoxide Parameter
essCO OBJECT-TYPE
SYNTAX	INTEGER (0..255)
ACCESS	read-only
STATUS	mandatory
DESCRIPTION "The concentration of carbon monoxide in the air, measured in parts per million.  The value 255 shall indicate an error condition or missing value."
::= {essNtcipAirQuality 1}

-- 3.14.2 Carbon Dioxide Parameter
essCO2 OBJECT-TYPE
SYNTAX	INTEGER (0..65535)
ACCESS	read-only
STATUS	mandatory
DESCRIPTION "The concentration of carbon dioxide in the air, measured in parts per billion.  The value 65535 shall indicate an error condition or missing value."
::= {essNtcipAirQuality 2}

-- 3.14.3 Nitrous Oxide Parameter
essNO OBJECT-TYPE
SYNTAX	INTEGER (0..255)
ACCESS	read-only
STATUS	mandatory
DESCRIPTION "The concentration of nitrous oxide in the air, measured in parts per million.  The value 255 shall indicate an error condition or missing value."
::= {essNtcipAirQuality 3}

-- 3.14.4 Nitrogen Dioxide Parameter
essNO2 OBJECT-TYPE
SYNTAX	INTEGER (0..255)
ACCESS	read-only
STATUS	mandatory
DESCRIPTION "The concentration of nitrogen dioxide in the air, measured in parts per billion.  The value 255 shall indicate an error condition or missing value."
::= {essNtcipAirQuality 4}

-- 3.14.5 Sulfur Dioxide Parameter
essSO2 OBJECT-TYPE
SYNTAX	INTEGER (0..65535)
ACCESS	read-only
STATUS	mandatory
DESCRIPTION "The concentration of sulfur dioxide in the air, measured in parts per billion.  The value 65535 shall indicate an error condition or missing value."
::= {essNtcipAirQuality 5}

-- 3.14.6 Ozone Parameter
essO3 OBJECT-TYPE
SYNTAX	INTEGER (0..255)
ACCESS	read-only
STATUS	mandatory
DESCRIPTION "The concentration of ozone in the air, measured in parts per one hundred billion.  The value 255 shall indicate an error condition or missing value."
::= {essNtcipAirQuality 6}

-- 3.14.7 Particulate Matter Parameter
essPM10 OBJECT-TYPE
SYNTAX	INTEGER (0..65535)
ACCESS	read-only
STATUS	mandatory
DESCRIPTION "The concentration of small particulate matter of 10 micrometers or less in diameter in the air, measured in micrograms per cubic meter.  The value 65535 shall indicate an error condition or missing value."
::= {essNtcipAirQuality 7}

-- 3.15 WATER QUALITY PARAMETERS
essNtcipWaterQuality  OBJECT IDENTIFIER ::= { essNtcip 13 }
-- This node contains objects used for monitoring water quality conditions.  Appropriate agencies have 
-- been contacted to assist in the development of these objects for future versions.

END         -- ESS-MIB
