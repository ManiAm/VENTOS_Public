-- 2.1 DATA COLLECTION AND MONITORING (DCM) MIB HEADER INFORMATION

-- Filename:    1206v0122.mib
-- Description: This MIB defines definitions of management information related to a Data 
--              Collection and Monitoring device.
-- Source:      NTCIP 1206v01.22b
-- MIB Revision History:
-- 09/27/04     Created file form supplied source.  
--              Changed module name to match source
--              Changes status of entry defintions and index objects to mandatory to
--              eliminate incompatible status errors
--              Restructured IMPORTS around NTCIP8004-A-2004 
--              
--
-- NOTE - THIS MIB WAS SYNTAX CHECKED WITH AN ADDITIONAL OPTION SWITCH TO ALLOW THE USE
-- OF "STATUS not-accessible" FOR SEVERAL LEAF/COLUMNAR OBJECTS.  
--
-- ONE SHOULD BE ALSO AWARE THAT THE UNBOUNDED OCTET STRING IN dcmMEPollNow, "dcmLDData",
-- AND "dcmData" SHOULD HAVE A SIZE CONSTRAINT TO ELIMINATE SYNTAX CHECKING WARNINGS. 
-- WHILE SNMPV1 DOES NOT IMPOSE A LIMIT, SNMPV2 SPECIFIES A LIMIT OF 65535.
--
--
--Copyright 2004 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************

-- Use the following 'SMICng' command from DOS command line to compile:
--  'SMICng -0 -C4 -C5 -C6 -CG -CK -CU -F 1206.dat 1206.mib'
--
-- Use the following 'SMIC' command from DOS command line to compile
--  and create an OID listing (based on OID number ordering of objects):
-- 'SMIC /N /0 /3 /4 /5 /E /F 1206.dat 1206.mib
--
-- Use the following 'SMIC' command from DOS command line to compile
--  and create an OID listing (based on alphabetical ordering of objects):
-- 'SMIC /L /0 /3 /4 /5 /E /F 1206.dat 1206.mib


--Uncomment out the following statements to compile this MIB from a 
-- DOS command line.
-- only uncomment for SMICng #SNMPv1
-- uncomment for SMIC/SMICng #include "rfc1155.smi" 
-- uncomment for SMIC/SMICng #include "rfc1212.smi" 
-- uncomment for SMIC/SMICng #include "nema.smi" 
-- uncomment for SMIC/SMICng #include "tmib-II.smi" 
--uncomment out the following statements down to here

--Data Collection and Monitoring MIB
DCM-MIB1 DEFINITIONS ::= BEGIN

--Import statements
IMPORTS
  Counter
  --, IpAddress
    FROM RFC1155-SMI

  OBJECT-TYPE
    FROM RFC-1212

  --DisplayString    -need to be REMed out when using with SMIC compiler
  --  FROM RFC-1213-MIB -need to be REMed when using with SMIC compiler
  --TRAP-TYPE
  --  FROM RFC-1215

  --devices
  --  FROM TMIB-II

  --EntryStatus, OwnerString, OerString,
  --Byte, UByte, Short, Ushort, Long, Ulong
  --  FROM NEMA-SMI

  --controller-localTime
  --  FROM GLOBAL-MIB;
  --;

--SMI OBJECT-TYPE
--DisplayString ::= OCTET STRING (SIZE(0..127))

--DCM-related Object Definitions
--dcm OBJECT IDENTIFIER ::= {devices 9}

  dcm
    FROM NTCIP8004-A-2004 ;

-- 2.2 DCM SYNTAX DEFINITIONS (TYPE ASSIGNMENTS)
-- This section contains SNMPv1 'Type Assignments'.  It provides a mechanism
-- to define a 'Type' once and allows for referencing of that defined type
-- in other object/table definitions.

-- 2.2.1 Table Row Maintenance (DcmRowStatus)
DcmRowStatus ::= INTEGER
{
 active (1), 
 notInService (2),
 notReady (3),
 createAndGo (4),
 createAndWait (5),
 destroy (6)
}
--This object is intended to provide the same functionality as the RowStatus
-- object defined in SNMPV2.  It shall operate in the same manner as defined
-- in SNMPV2.
--
--The 'action' states can be written, but not read:
--createAndGo: indicates that the agent should accept the row values
-- specified,create items within the row and place the row into service (or 
-- activate it)
--
--createAndWait: indicates that the agent should accept the values specified
-- (if any) and, create items within the row, but not place the row 
-- in service. 
--
--destroy:  indicates that the agent should remove the row from service and 
-- then delete it.
--
--The 'desired' states can be written and read:
--notInService: indicates that the row has been suspended. That is, the 
-- row does not exist.
--
--active: indicates that the row exists and can be used.
--
--The 'current' state can only be read:
--notReady: indicates that the row does not contain values for all columnar 
-- objects in the row that are needed for an agent to act upon.

-- 2.2.2 Time Tag Index (DcmTimeTagIndex)
DcmTimeTagIndex ::= INTEGER (0..4294967295)
--SMIC compiler will not allow using 'counter' as an index for tables.
--  There are table structures defined as not-accessible solely for
--  the purposes of data file storage.  DcmTimeTagIndex should be the exact
--  definition as 'counter' from RFC1155.smi.

-- 2.2.3 Maximum Number Of Rows (DcmMaxNumRows)
DcmMaxNumRows ::= INTEGER (0..65535)


--This value represents the maximum number of rows a table is allowed to have.

-- 2.2.4 Current Number Of Rows (DcmMaxNumRows)
DcmCurNumRows ::= INTEGER (0..65535)

--This value represents the current number of rows existing in a table.

-- 2.2.5 IO Board Number (DcmIOBoardNum)
DcmIOBoardNum ::= INTEGER (1..255)

--This value represents a unique number from the 'dcm IO Board Configuration 
-- Table' for each IO Board that has been installed within the dcm device.  
-- This number is assigned by the device and must be sequential.

-- 2.2.6 IO Board Function (DcmIOBoardFtn)
DcmIOBoardFtn ::= INTEGER (1..255)
	
--This value represents the function of each specified IO board in the 
-- IO Board Configuration Table. 
-- This number is assigned by the device.

-- 2.2.7 Logical IO Number (DcmLogIONum)
DcmLogIONum ::= INTEGER (1..255)

--Indicates a unique number assigned to each physical IO channel in the 'dcm 
-- Physical To Logical IO Mapping Table.  It provides a link to this IO 
-- channel for other objects/tables within this MIB as required.  This is 
-- assigned by the device (it is strongly recommended that it is assigned 
-- sequentially).

-- 2.2.8 IO Parameter Type (DcmIOParamType)
DcmIOParamType ::= INTEGER 
{
 other (1), 
 debounce (2), 
 deadtime (3),
 sensitivityGain (4),
 onThreshold (5),
 offThreshold (6),
 onHysteresis (7),
 offHysteresis (8),
 minOnTime (9),
 minOffTime (10),
 maxOnTime (11),
 maxOffTime (12),
 adOffset (13),
 scanTime (14),
 sensorLength (15),
 sensorWidth (16),
 sensorHeight (17),
 sensorDepth (18),
 sensorAngle (19), 
 ioCal (20),
 frequency (21),
 memoryWrap (22),
 dataStorageMediaAvailable (23),
 dataStorageMediaUsed (24)
}
--An enumeration used to identify a type of IO Parameter.  Refer to 
-- DcmIOParamValue for a description of each.

-- 2.2.9 IO Parameter Value (DcmIOParamValue)
DcmIOParamValue  ::= INTEGER (0..4294967295)

--Indicates the value for the selected IO parameter. These parameters are 
--typically used to help process and make adjustments to an IO.    If an 
--application tries to set an invalid value for a particular IO parameter, an 
--application error code of 'Out of range' shall be set.

--The following further defines each parameter:
-- (ms=milliseconds, us=microseconds, mm=millimeters, Mhz=megahertz)
--other(1)=not defined below.
--debounce(2)= (0-65535ms) the amount of time that input transitions shall be 
-- ignored relative to the last transition of the IO.
--deadtime(3)= (0-65535ms) the amount of time that input transitions shall be 
-- ignored relative to the first transition of the IO.
--sensitivityGain(4)= (0-100%) the percent of full-scale to set an IO gain or -- sensitivity adjustment
--onThreshold(5)= (0-100%) the percent of full-scale to set a level at which 
-- an IO shall be considered active
--offThreshold(6)= (0-100%) the percent of full-scale to set a level at which -- an IO shall be considered inactive
--onHysteresis(7), (0-100%) the percent of full-scale which sets a threshold 
-- level above the 'off' point to trigger another 'on' to prevent an IO from 
-- continuously turning on-off
--offHysteresis(8)= (0-100%) the percent of full-scale which sets a threshold -- level below the 'on' point to trigger another 'off' to prevent an IO from 
-- continuously turning on-off
--minOnTime(9)= (0-65535ms) the minimum amount of time an input must remain on -- to be considered a valid on
--minOffTime(10)= (0-65535ms) the minimum amount of time an input must remain 
-- off to be considered a valid off
--maxOnTime(11)= (0-16777215ms) the maximum amount of time an IO is allowed to -- remain on before triggering an action (sensor input stuck on)
--maxOffTime(12)= (0-16777215ms) the maximum amount of time an IO is allowed
-- to remain off before triggering an action (sensor input stuck off)
--adOffset(13)= (0-100%) the percent of full-scale to set an analog to digital -- converter's offset voltage
--scanTime(14)= (0-3600000000us) the time frequency in which an IO channel is -- sampled
--sensorLength(15)= (0-65535mm) the length of the active portion of an IO 
-- oriented in the same direction as vehicles traverse the array
--sensorWidth(16)= (0-65535mm) the width of the active portion of an IO 
-- oriented perpendicular to the direction of vehicles traversing the array
--sensorHeight(17)= (0-65535mm) the height above the roadway in which an IO is 
-- mounted
--sensorDepth(18)= (0-65535mm) the depth below the roadway in which an IO is 
-- mounted
--sensorAngle(19)=  (0-1296000seconds) the angle in seconds (up to 360degrees) 
-- which defines the angle of an IO
--ioCal(20), (0-100000) a multiplier in .001 between 0 and 100.000 used to 
-- scale an IO
--frequency(21), (0-4294967295hz, 4 octets) the frequency assigned to an IO 
--channel
--memoryWrap(22), (0=off, 1=on) enables/disables 'memory wrap' for the 
-- specified storage media (memory wrap is defined as the process in which 
-- older files are deleted or wrapped out from a storage media to make room 
-- for newer files)
--dataStorageMediaAvailable(23)= (0-4294967295) indicates the number of bytes 
-- available on this storage media.  This is a read-only parameter, writes to 
-- this parameter shall be ignored (a dcm error code of readOnly shall be set).
--dataStorageMediaUsed(24)= (0-4294967295) indicates the number of bytes used 
-- on this storage media.  This is a read-only parameter, writes to this 
-- parameter shall be ignored (a dcm error code of readOnly shall be set).

--On % full scale values, the "GET" value may not be same as the requested 
--"SET" value since the implemented scale is IO and device-specific.  "

-- 2.2.10 Array Number (DcmArrayNum)
DcmArrayNum ::= INTEGER (1..255)

--This object represents a unique number for each sensor array that is defined 
-- within the device in the 'dcm Logical IO To Array Mapping Table'.  It is 
-- strongly suggested that the array numbers are assigned sequentially.

-- 2.2.11 Array Parameter Type (DcmArrayParamType)
DcmArrayParamType ::= INTEGER 
{
 other (1),
 maxAxleSpacing (2),
 vehicleAxleRatio (3),
 singleAxleTimeout (4),
 maxVehicleLength (5),
 wimCalFactor (6),
 calFilePointer (7),
 arraySpeedCal (8)
}
--Indicates the type of parameter associated with an array. One or more types 
--can be associated with an array.  The values are:
-- other (1),= not defined below.
-- maxAxleSpacing (2),= The longest axle spacing (in millimeters) that would 
-- be expected on any vehicle to traverse the array.  This parameter is 
-- typically used to end a vehicle if there is no presence sensor used in the -- array.
-- vehicleAxleRatio (3),= The number of detected axles which shall be considered to 
--  constitute a vehicle.  This parameter is typically used in arrays that can
--  only detect axles. 
-- singleAxleTimeout (4)= The amount of time from the last axle strike (in 
--  milliseconds) that must elapse before another axle strike to end a 
--  vehicle.  This parameter is typically used with arrays that do not use a 
--  presence sensor to separate vehicles or cannot calculate a speed to use 
--  the maxAxleSpacing parameter.
-- maxVehicleLength (5),= This parameter defines the maximum expected vehicle 
--  length (in mm) to traverse the sensor array.  It is typically used to end 
--  a vehicle in a situation where  the sensor used to calculate vehicle 
--  length may be stuck on.
-- wimCalFactor (6),= This parameter defines a multiplier (0.000 to 65.535) to 
--  be applied to weights calculated by an array.  This is a discrete number 
--  and has no units.
-- calFilePointer (7)= The file name specified in the dcmParameterFileName 
--  points to a file containing implementation-specific calibration parameters 
-- (e.g. classification scheme, WIM autocalibration scheme).  object. The 
--  value of the dcmParameterValue shall be ignored. 
-- arraySpeedCal (8) = this enumeration was added to allow encoding of an 
--  array speed calibration change (refer to dcmArraySpeedCalFactor in the 
--  'Array Speed Calibration Table') to be encoded into the 'Array Parmater 
--  Change Record Table' and written to a dcm data file. It shall not be used 
--  in this table."

-- 2.2.12 Array Parameter Value (DcmArrayParamValue)
 DcmArrayParamValue ::= INTEGER (0..16777215)

--Indicates the value associated with an array parameter type as 
-- specified by a DcmArrayParamType object.  The acceptable value ranges and 
-- units differ depending on the value of the dcmParameterType object value.  
-- The acceptable values and UNITs per parameter type are: 
-- maxAxleSpacing = 0 to 65535 in millimeter
-- vehicleAxleRatio = 1.00 to 655.35 as a divisor (e.g., 2.00 specifies that 2 
--  axles constitute 1 vehicle)
-- singleAxleTimeout = 0 to 65535 in milliseconds
-- maxVehicleLength = 0 to 65535 in millimeters
-- wimCalFactor = 0.000 to 100.000 as a multiplier
-- calFilePointer = The DcmArrayParamValue is meaningless when the 
--  DcmArrayParamType object is set to 'calFilePointer'.  The 
--  DcmArrayParamFileName object should be read to obtain an octet string 
--  identifying the name of a file which contains implementation-specific 
--  calibration factors.  
-- arraySpeedCal= Refer to dcmArraySpeedCalFactor in the 'Array Speed 
--  Calibration Table'

-- 2.2.13 Array Parameter File Name (DcmArrayParamFileName)
DcmArrayParamFileName ::= OCTET STRING (SIZE (0..255))

--Indicates a file name that contains array parameter calibration information. 
-- This information is most likely implementation-specific.  The value of this 
-- object is only meaningful, if the value of the Array Parameter Type 
-- (dcmAPType) object is set to 'calFilePointer', otherwise this value shall 
-- be ignored.

-- 2.2.14 Filter Number (DcmFilterNum)
DcmFilterNum ::= INTEGER (1..255)

--This object indicates a filter number assigned to filters defined within 
-- this dcm device from the 'dcm Filter Configuration Table'.

-- 2.2.15 Study Number (DcmStudyNum)
DcmStudyNum ::= INTEGER (1..255)

--This object represents a unique number for each study that is defined within 
-- the dcm device in the 'dcm Study Configuration Table'.  It is recommended 
-- to assign this value sequentially, however when studies are deleted, there 
-- could be gaps in the indexes.  It is recommended to use the deleted study 
-- number as the next one to assign as an attempt to keep these indexes 
-- sequential.

-- 2.2.16 File Study Index (DcmFileStudyIndex)
DcmFileStudyIndex ::= INTEGER (0..255)

--Identifies a file structure number defined within the 'dcm File Structure 
-- Table'.  A value of zero (0) indicates that no data shall be recorded and 
-- the study is to be used for Monitor Modes.

-- 2.2.17 File Structure Number (DcmFileStrucNum)
DcmFileStrucNum ::= INTEGER (1..255)

--This object points to a defined file structure in the 'dcm File Structure 
-- Table'.  It is highly recommended that the application try to keep this 
-- number sequential (reuse numbers that have been deleted).

-- 2.2.18 Binned Filter Number (DcmBinnedFilterNum)
DcmBinnedFilterNum ::= INTEGER (1..255)

--This object represents a unique number for each binned filter that has been 
-- defined in the 'dcm Binned Filter Definition Table) within the device.  It 
-- is strongly suggested that the numbering is assigned sequentially.  This 
-- number can never exceed the maximum number of bins for all studies object 
-- (dcmMaxNumBins).

-- 2.3 VEHICLE CRITERIA NODE
--DCM Vehicle Criteria Node
dcmVehCriteria OBJECT IDENTIFIER ::= {dcm 1}

-- This node identifies the parameters that are used to define vehicle 
--  criteria that can be used to configure Binned Studies, PVR Studies and 
--  Filters.  

-- These parameters are not intended to be  manipulated directly by an 
--  application.  They are defined to allow assignment of an OID to reference 
--  them in other places.  They are defined in this section because they were
--  not required to be defined as regular objects elsewhere in this standard.

-- Objects defined as an Integer can be used in the Filter Config Table and 
--  the Binned Filter Definition Table.  Objects of any type can be used 
--  in the PVR Study Configuration Table.  

-- Even though an object is defined in this node, a device may not allow 
--  using that object in one of the stated tables (as it may not be sensible).  
--  The device shall return a dcm application error code of 'invalidOption'
--  for any object not allowed in one of the tables.  
-- The Vehicle Criteria Table shall indicate which vehicle parameters
--  (both within this MIB and externalto this MIB) are supported and for
--  what application (Binned Studies, PVR Studies or filters).

-- Note that objects that are only defined as elements of a table 
--  (e.g. Array Number (DcmArrayNum)) may also be used within the 
--  Vehicle Criteria Table.  The OID's for these type of objects should
--  be taken from the table from which that object is first defined
--  (e.g. Array Number is first defined in the Logical IO To Array Map Table
--   as dcmIOAMArrNum).  Therefore if Array Number is supported by this
--  device, then the OID for dcmIOAMArrNum should be used in the 
--  Vehicle Criteria Table.  Other objects (within this standard) included 
--  in this category are dcmPLMLogIONum and dcmFCFilterNum. The controller
--  local time zone object from the Global Objects (1201-2.4.7, 
--  controller-localTime) is also included in this category.

-- Each object defined in this section can be either a single-occurrence or
--  multi-occurrence object when used to configure a PVR Study.  
-- A single-occurrence object has only one instance when stored in the PVR 
--  data (such as vehicle speed).  
-- A multi-occurrence object shall consist of multiple occurrences of
--  the object (such as axle weights).
-- Unless otherwise specified, all objects shall be defined as a 
--  single-occurrence object.

-- A single-occurrence object  has only one instance of the 
--  defined parameter in the PVR structure, it shall be encoded as [(value)].
--  The length of the 'value' is specified by the  definition of the object.  
--  (e.g. if an object is defined as INTEGER (1..65535), it must always be
--  stored using two octets). There must always be that number of octets 
--  used to store this parameter (even if the value can be represeneted 
--  in less octets).  
-- A multi-occurrence object  may have more than one instance 
--  of the defined parameter in the PVR structure.  This encoding shall always
--  start with a single octet to specify the number of occurrences for 
--  this parameter (cannot exceed 255 occurrences of any parameter).  
--  The multiple occurrences for this parameter must 
--  be stored sequentially (e.g. if axle spacings then axsp1, axsp2, axsp3 …).  
--  The length of each value is specified in the definition of the object
--   and all occurrences of this parameter must be the same length.  
--   The number of occurrences octet may be set to 0 to indicate that 
--   there are no parameters of this type stored.  This encoding allows 
--   Pvr Record 1 to specify 5 axle weights for a truck and Pvr Record 2 
--   to only specify 2 axle weights for a car.  The encoding becomes:
--   [(# of occurrences=n)(value 1)(value 2)…(value n)].

-- For either single or multi-occurrence objects, if the specified object 
--  is an integer, the value field shall only consist of the data without
--  a tag or length field as defined in BER encoding.  If the specified
--  object is an octet string, it shall be stored with a tag and length field
--  as defined by BER encoding for octet strings.  A BER "NULL" may be
--  used in place of any octet string object that could not be determined
--  by the device.  This allows for specifying multiple instances of octet 
--  strings of varying sizes.  A "NULL" is used as opposed to specifying 
--  an OCTET STRING of size 0 octets because an OCTET STRING of size 0
--  octets may be a valid value for the specified parameter.

-- 2.3.1 Maximum Number Of Vehicle Criteria Table Rows
dcmVCTMaxNumRows OBJECT-TYPE
 SYNTAX DcmMaxNumRows
 ACCESS read-only
 STATUS mandatory
 DESCRIPTION
 "Indicates the maximum number of rows allowed for the Vehicle Criteria Table."
::= {dcmVehCriteria 1}

-- 2.3.2 Current Number Of Vehicle Criteria Table Rows
dcmVCTCurNumRows OBJECT-TYPE
 SYNTAX DcmCurNumRows
 ACCESS read-only
 STATUS mandatory
 DESCRIPTION
 "Indicates the current number of rows existing in the Vehicle Criteria Table."
::= {dcmVehCriteria 2}

-- 2.3.3 Vehicle Criteria Table 
dcmVehCriteriaTable OBJECT-TYPE
 SYNTAX   SEQUENCE OF DcmVehCriteriaEntry
 ACCESS   not-accessible
 STATUS   optional
 DESCRIPTION
 "This is a single-indexed table.  It contains all the OID's (from this MIB and also can contain OID's from other MIBS) of all objects that this dcm device shall support for vehicle criteria to be used in configuring binned studies, pvr studies and filters."
::= {dcmVehCriteria 3}

dcmVehCriteriaEntry OBJECT-TYPE
 SYNTAX   DcmVehCriteriaEntry 
 ACCESS   not-accessible
 STATUS   mandatory
 DESCRIPTION "..."
 INDEX {dcmVCIndex}
::= {dcmVehCriteriaTable 1}

DcmVehCriteriaEntry  ::= SEQUENCE 
{
 dcmVCIndex    INTEGER,
 dcmVCOID      OBJECT IDENTIFIER,
 dcmVCBitMap   INTEGER
}

-- 2.3.3.1 Vehicle Criteria Index
dcmVCIndex OBJECT-TYPE
 SYNTAX INTEGER (1..255)
 ACCESS read-only
 STATUS mandatory
 DESCRIPTION
 "Indicates the only index into this table. It represents a unique sequential number for each row in this table."
::= {dcmVehCriteriaEntry 1}

-- 2.3.3.2 Vehicle Criteria OID
dcmVCOID OBJECT-TYPE
 SYNTAX   OBJECT IDENTIFIER
 ACCESS   read-only
 STATUS   mandatory
 DESCRIPTION
 "This field contains the OID of a Vehicle Criteria object that is supported by this device.  The OID specified must be a full OID from the root of the iso tree, relative OID's cannot be used.  This allows referring to objects outside of this MIB.  The specified OID can also be an OID from a table (if the object is only defined within a table (e.g. Array Number), but it shall be the OID of the object from the table in which the specified object is defined (e.g. if Array Number is to be used, the OID shall be taken from the Logical IO To Array Map Table"
::= {dcmVehCriteriaEntry 2}

-- 2.3.3.3 Vehicle Criteria Support BitMap
dcmVCBitMap OBJECT-TYPE
 SYNTAX  INTEGER (0..255)  --Bitmap
 ACCESS  read-only
 STATUS  mandatory
 DESCRIPTION
 "This bitmap indicates which set of functionality for each specified OID (dcmVCOID) this device supports.  Setting a bit to one (1) indicates that the associated functionality is supported.  All unused bits shall be reserved.
Note that the options pvrStudySingle and pvrStudyMulti are included to specifically address any objects that are supported by the device for PVR Studies, but do not specify if it is a single-occurrence or multi-occurrence object in it's definition.
The values are:
bit 0 – other
bit 1 – binnedStudy, the object specified by dcmVCOID is supported to configure binned studies.
bit 2 – pvrStudySingle, the object specified by dcmVCOID is supported to configure pvr studies and is a single-occurrence object. Note that both pvrStudySingle and pvrStudyMulti cannot be selected for the same object.  Only one of the two options may be selected for the specified object.
bit 3 – pvrStudyMulti, the object specified by dcmVCOID is supported to configure pvr studies and is a multi-occurrence object.  Note that both pvrStudySingle and pvrStudyMulti cannot be selected for the same object.  Only one of the two options may be selected for the specified object.
bit 4 – filters, the object specified by dcmVCOID is supported to configure filters."
::= {dcmVehCriteriaEntry 3}

-- 2.3.4 Axle Number
dcmAxleNumber OBJECT-TYPE
 SYNTAX  INTEGER (1..255)
 ACCESS  not-accessible
 STATUS  optional
 DESCRIPTION
 "Indicates the axle number of a vehicle that is being referenced. This is a discrete number and has no units.  A value of one (1) indicates the first axle of a vehicle detected by the sensor array.  The highest value that this object can reference is defined by the value of the dcmMaxNumAxles object."
::= {dcmVehCriteria 4}

-- 2.3.5 Number of Axles
dcmNumAxles OBJECT-TYPE
 SYNTAX  INTEGER (0..255)
 ACCESS  not-accessible
 STATUS  optional
 DESCRIPTION
 " Indicates the number of axles on a vehicle. This is a discrete number and has no units. A value of zero (0) indicates that no axles were detected. The highest value that this object can reference is defined by the value of the dcmMaxNumAxles object."
::= {dcmVehCriteria 5}

-- 2.3.6 Vehicle Class
dcmVehicleClass OBJECT-TYPE
 SYNTAX  INTEGER (0..255)
 ACCESS  not-accessible
 STATUS  optional
 DESCRIPTION
 "Indicates a system-wide unique classification of a vehicle. Any or all vehicle parameters (such as vehicle length, axle spacings,…) can be used to derive this classification. This is a discrete number and has no units."
::= {dcmVehCriteria 6}

-- 2.3.7 Vehicle Speed 
dcmVehicleSpeed OBJECT-TYPE
 SYNTAX  INTEGER (0..65535)
 ACCESS  not-accessible
 STATUS  optional
 DESCRIPTION
 "Indicates the vehicle speed, in cm/sec."
::= {dcmVehCriteria 7}

-- 2.3.8 Vehicle Length
dcmVehicleLength OBJECT-TYPE
 SYNTAX  INTEGER (0..65535)
 ACCESS  not-accessible
 STATUS  optional
 DESCRIPTION
 "Indicates the overall length of a vehicle, in cm, from the physical start to the physical end of the vehicle."
::= {dcmVehCriteria 8}

-- 2.3.9 Vehicle Front Overhang
dcmFrontOverhang OBJECT-TYPE
 SYNTAX  INTEGER (0..65535)
 ACCESS  not-accessible
 STATUS  optional
 DESCRIPTION
 "Indicates the front overhang of a vehicle which is measured from the physical start of a vehicle to its first axle (center), units are cm."  
::= {dcmVehCriteria 9}

-- 2.3.10 Vehicle Rear Overhang
dcmRearOverhang OBJECT-TYPE
 SYNTAX  INTEGER (0..65535)
 ACCESS  not-accessible
 STATUS  optional
 DESCRIPTION
"Indicates the rear overhang of a vehicle which is measured from last axle(center) of a vehicle to it the physical end, units are cm."  
::= {dcmVehCriteria 10}

-- 2.3.11 Axle Spacing 
dcmAxleSpacing OBJECT-TYPE
 SYNTAX  INTEGER (0..65535)
 ACCESS  not-accessible
 STATUS  optional
 DESCRIPTION
 "Indicates the spacing between adjacent axles (from the center of one axle to the center of the next axle), measured in cm.  This is a multiple-occurrence object where the number of occurrences is one less than the number of axles detected for this vehicle.  
A value of zero (0) shall be recorded for any axle spacings that cannot be determined."
::= {dcmVehCriteria 11}

-- 2.3.12 Vehicle Wheelbase
dcmVehWheelbase OBJECT-TYPE
 SYNTAX  INTEGER (0..65535)
 ACCESS  not-accessible
 STATUS  optional
 DESCRIPTION
 "Indicates the distance from the first to the last axle (center to center) of a vehicle.  Units are cm. 
A value of zero (0) shall be recorded if the vehicle wheelbase cannot be determined."
::= {dcmVehCriteria 12}

-- 2.3.13 Vehicle Clearance
dcmVehClearance OBJECT-TYPE
 SYNTAX  INTEGER (0..255)
 ACCESS  not-accessible
 STATUS  optional
 DESCRIPTION
 "Indicates the clearance of the vehicle above ground measured from the lowest point of the vehicle excluding tire and wheel, in cm. 
A value of zero (0) shall be recorded if the vehicle clearance cannot be determined."
::= {dcmVehCriteria 13}

-- 2.3.14 Vehicle Height
dcmVehicleHeight OBJECT-TYPE
 SYNTAX  INTEGER (0..65535)
 ACCESS  not-accessible
 STATUS  optional
 DESCRIPTION
 "Indicates the overall height of the vehicle from the ground to its highest point including load, measured in cm.
A value of zero (0) shall be recorded if the vehicle height cannot be determined."
::= {dcmVehCriteria 14}

-- 2.3.15 Axle Width
dcmAxleWidth OBJECT-TYPE
 SYNTAX  INTEGER (0..65535)
 ACCESS  not-accessible
 STATUS  optional
 DESCRIPTION
 "Indicates the overall width of an axle from outside edge to outside edge of the outer tires on a vehicle, measured in cm.  This is a multiple occurrence object where the number of occurrences is equal to the number of axles detected for this vehicle.  
A value of zero (0) shall be recorded for any axle widths that cannot be determined."
::= {dcmVehCriteria 15}

-- 2.3.16 Vehicle Width
dcmVehicleWidth OBJECT-TYPE
 SYNTAX  INTEGER (0..65535)
 ACCESS  not-accessible
 STATUS  optional
 DESCRIPTION
 "Indicates the width of the vehicle at the widest point including load. Units are cm.
A value of zero (0) shall be recorded if the vehicle width cannot be determined."
::= {dcmVehCriteria 16}

-- 2.3.17 Axle Tire Count
dcmAxleTireCount OBJECT-TYPE
 SYNTAX  INTEGER (0..255)
 ACCESS  not-accessible
 STATUS  optional
 DESCRIPTION
 "Indicates the total number of tires per axle.  Note that for dual-tire axles, this value shall be 4. 
This is a multiple occurrence object where the number of occurrences is equal to the number of axles detected for this vehicle.  
A value of zero (0) shall be recorded for any tire counts per axle that cannot be determined."
::= {dcmVehCriteria 17}

-- 2.3.18 Axle Tire Track
dcmAxleTireTrack OBJECT-TYPE
 SYNTAX  INTEGER (0..65535)
 ACCESS  not-accessible
 STATUS  optional
 DESCRIPTION
 "Indicates the distance from the right-most edge of the sensor array to the right-most tire per axle.  Units are in cm.
This is a multiple occurrence object where the number of occurrences is equal to the number of axles detected for this vehicle.  
A value of zero (0) shall be recorded for any axle tire track that cannot be determined."
::= {dcmVehCriteria 18}

-- 2.3.19 Vehicle Gap
dcmVehicleGap OBJECT-TYPE
 SYNTAX  INTEGER (0..16711425)
 ACCESS  not-accessible
 STATUS  optional
 DESCRIPTION
 "Indicates the time separation between 2 vehicles, measured in milliseconds.  This value is measured from the physical end of the preceding vehicle to the physical start of the current vehicle.  A value of zero (0) is used where the gap cannot be determined.  If the detected value exceeds the maximum value of this object, the maximum value shall be used."
::= {dcmVehCriteria 19}

-- 2.3.20 Vehicle Headway
dcmVehicleHeadway OBJECT-TYPE
 SYNTAX  INTEGER (0..1671142)
 ACCESS  not-accessible
 STATUS  optional
 DESCRIPTION
 "Indicates the time separation between 2 vehicles, measured in milliseconds.  This value is measured from the physical start of the preceding vehicle to the physical start of the current vehicle.  A value of zero (0) is used where the gap cannot be determined.  If the detected value exceeds the maximum value of this object, the maximum value shall be used."
::= {dcmVehCriteria 20}

-- 2.3.21 Left Wheel Weight 
dcmLeftWheelWeight OBJECT-TYPE
 SYNTAX  INTEGER (0..65535)
 ACCESS  not-accessible
 STATUS  optional
 DESCRIPTION
 "Indicates the weight of the left wheel (left group of one or more tires on the same axle relative to the direction of travel), measured in kilograms. 
This is a multiple occurrence object where the number of occurrences is equal to the number of axles detected for this vehicle.  
A value of zero (0) shall be recorded for any axle wheel weights that cannot be determined."
::= {dcmVehCriteria 21}

-- 2.3.22 Right Wheel Weight 
dcmRightWheelWeight OBJECT-TYPE
 SYNTAX  INTEGER (0..65535)
 ACCESS  not-accessible
 STATUS  optional
 DESCRIPTION
 "Indicates the weight of the right wheel (right group of one or more tires on the same axle relative to the direction of travel), measured in kilograms. 
This is a multiple occurrence object where the number of occurrences is equal to the number of axles detected for this vehicle.  
A value of zero (0) shall be recorded for any axle wheel weights that cannot be determined."
::= {dcmVehCriteria 22}

-- 2.3.23 Axle Weight 
dcmAxleWeight OBJECT-TYPE
 SYNTAX  INTEGER (0..65535)
 ACCESS  not-accessible
 STATUS  optional
 DESCRIPTION
 "Indicates the weight of an axle, measured in kilograms. 
This is a multiple occurrence object where the number of occurrences is equal to the number of axles detected for this vehicle.  
A value of zero (0) shall be recorded for any axle weights that cannot be determined."
::= {dcmVehCriteria 23}

-- 2.3.24 Sensor Weights 
dcmSensorWeight OBJECT-TYPE
 SYNTAX  INTEGER (0..65535)
 ACCESS  not-accessible
 STATUS  optional
 DESCRIPTION
 "Indicates the weight calculated by a WIM sensor, measured in kilograms.  
This is a multiple occurrence object where the number of occurrences is equal to the number of axles detected for this vehicle multiplied by the number of WIM sensors in the array. The number of WIM sensors in the array is defined in the logicalIoArrayMappingTable.  The sequence of sensorWeight values within the data collection file is logicalIoNumber value and then axleNumber value (e.g., a 3-axle vehicle crosses a 2-sensor WIM array, it would be recorded as logicalIoNumber1-axleNumber1-sensorWeight value, logicalIoNumber1-axleNumber2-sensorWeight value, logicalIoNumber1-axleNumber3-sensorWeight value, logicalIoNumber2-axleNumber1-sensorWeight value, logicalIoNumber2-axleNumber2-sensorWeight value, logicalIoNumber2-axleNumber3-sensorWeight value).  The WIM logicalIoNumbers shall be listed in ascending order.
A value of zero (0) shall be recorded for any sensor weights that cannot be determined."
::= {dcmVehCriteria 24}

-- 2.3.25 Gross Vehicle Weight 
dcmGrossVehicleWeight OBJECT-TYPE
 SYNTAX  INTEGER (0..16711425)
 ACCESS  not-accessible
 STATUS  optional
 DESCRIPTION
 "Indicates the gross weight of a vehicle (the sum of all axle weights), measured in kilograms. A value of zero (0) shall be recorded, if the gross vehicle weight cannot be determined."
::= {dcmVehCriteria 25}

-- 2.3.26 Vehicle Sequence Number 
dcmVehicleSeqNum OBJECT-TYPE
 SYNTAX  INTEGER (0..65535)
 ACCESS  not-accessible
 STATUS  optional
 DESCRIPTION
 "A number assigned to each vehicle that traverses a sensor array.  The numbers are assigned sequentially over all sensor arrays. The value shall roll over to a value of 1 (1-65535). If a sequential number cannot be assigned, a value of zero (0) shall be used.    This number along with a time tag (controller-localTime) is used to uniquely identify vehicles.  For example, if a vehicle traverses sensor array 1 and is assigned sequence number 1, the next vehicle (regardless of which sensor array it traverses will be assigned sequence number 2."
::= {dcmVehCriteria 26}

-- 2.3.27 Vehicle Status Flag 
dcmVehicleStatusFlag OBJECT-TYPE
 SYNTAX  INTEGER (0..4294967295)  --Bitmap
 ACCESS  not-accessible
 STATUS  optional
 DESCRIPTION
 "Indicates a vehicle-specific status and warning information (e.g. unbalanced axle hits) for the specified vehicle.  Setting a bit to one (1) indicates that the associated condition is true.  The values are:
bit 0 – other
bit 1 – off/onScale – physical off scale sensor is triggered or the on scale sensor was NOT triggered.
bit 2 – overHeight – physical overheight sensor was triggered
bit 3 – speedChange – too much speed change detected between adjacent axles for this vehicle
bit 4 – partialAxle – something went wrong in the middle of processing an axle
bit 5 – unequalAxleCount – number of axles detected on each axle sensor is not the same.
bit 6 – tailgating – this vehicle follows the preceding vehicle too closely
bit 7 – wrongLane – this vehicle is in the wrong lane
bit 8 – runningScale – this vehicle bypassed the weigh-station incorrectly
bit 9 – notWimLane – this class of vehicle should not be in this lane
bit 10 – overlength – vehicle exceeds length threshold
bit 11 – overGVW – vehicle exceeds GVW weight threshold
bit 12 – randomSafety – vehicle randomly selected for Safety check
bit 13 – overSpeed - vehicle exceeds the speed threshold
bit 14 – late – vehicle arrives late at the next sensor array; used in conjunction with bits 18, 19, 20.
bit 15 – unexpected – vehicle arrives unexpectedly at the next sensor array
bit 16 – pastDue – vehicle didn't arrive at the next sensor array within the arrival threshold
bit 17 – noMatch – no vehicle match was found for this vehicle at this sensor array
bit 18 – badLateralPosition – error computing vehicle position (tire tracking)
bit 19 – noCompliance – no vehicle compliance structure found for this class of vehicle
bit 20 – overrideFail – failed to adjust the direction signs in time
bit 21 – wrongWay – vehicle went over the sensor array in an unexpected direction
bit 22- MinSpeed – too slow for data processing purposes
bit 23 – AxleProcessingError – internal error inside the vehicle processing software
bit 24 - MaxSpeed – too fast for data processing purposes
bit 25 - TooManyAxles – the value indicated in the dcmMaxAxles object has been exceeded
bit 26 - SensorOrderError – at least one of the sensors within the array was not activated in the expected order, e.g., only the upstream sensor, or only the downstream sensor was activated, or a sensor was activated by another lane movement
bit 27 – MinAxleSpacing – the detected value for the axle spacing was below the threshold for minAxleSpacing
bit 28 – MinFirstAxleSpacing - the detected value for the first axle spacing was below the threshold for minFirstAxleSpacing
All unused bits are reserved."
::= {dcmVehCriteria 27}

-- 2.3.28 Axle Weight Violation Code 
dcmAxleWeightViolationCode OBJECT-TYPE
 SYNTAX  INTEGER (0..16711425)  -- bitmap
 ACCESS  not-accessible
 STATUS  optional
 DESCRIPTION
 "Indicates axle-specific violations (e.g., axle overweight) for the specified vehicle.  Setting a bit to one (1) indicates that the associated condition is true.  This object is a bitmap.  
The bit assignments are:
OtherWeightViolation (bit 0) – if a weight violation not defined below has been detected.
SteeringViolation (bit 1) – if the allowable steering axle weight has been exceeded and if this axle is part of a steering axle group.  
SingleAxleViolation (bit 2) – if the allowable single axle weight has been exceeded and if this axle is a single axle.
TandemAxleViolation (bit 3) - if the allowable tandem axle weight has been exceeded and if this axle is part of a tandem axle group.
TridemAxleViolation (bit 4) - if the allowable tridem axle weight has been exceeded and if this axle is part of a tridem axle group.
QuadremAxleViolation (bit 5) - if the allowable quadrem axle weight has been exceeded and if this axle is part of a quadrem axle group.
AxleBalanceViolation (bit 6) – if the difference between axle weights within an axle group exceeds a pre-defined threshold.
AxleGroupIndividualViolation (bit 7) – if the maximum weight 'individual axle' threshold for an individual axle within an axle group has been exceeded.
BridgeViolation (bit 8) –if this axle is part of any combination of axles which exceed the maximum bridge weight threshold.
WheelViolation (bit 9) -  if the allowable wheel weight for any single wheel (group of tires) on an axle has been exceeded.
WheelImbalanceViolation (bit 10) – if the imbalance between wheel weights on an axle exceeds a pre-defined threshold.
The definition of what constitutes a violation is NOT defined by this standard.  If a violation has been detected the corresponding bit shall be set to 1.  Thus, if no violation has been detected, the value of this object is zero (0).
This object is a multiple-occurrence object where the number of occurrences is equal to the number of axles detected for this vehicle.
All unused bits are reserved."
::= {dcmVehCriteria 28}

-- 2.3.29 Vehicle Acceleration 
dcmVehicleAcceleration OBJECT-TYPE
 SYNTAX  INTEGER (-32768..32767)
 ACCESS  not-accessible
 STATUS  optional
 DESCRIPTION
 "Indicates the acceleration/deceleration of a vehicle, measured in cm/s². Deceleration is defined as negative acceleration.  A value of -32768 shall be recorded, if the acceleration of a vehicle cannot be determined."
::= {dcmVehCriteria 29}


-- 2.3.30 Number of Vehicle IDs 
dcmNumVehicleIDs OBJECT-TYPE
 SYNTAX  INTEGER (0..255)
 ACCESS  not-accessible
 STATUS  optional
 DESCRIPTION
 "Indicates the total number of vehicle IDs associated with a vehicle."
::= {dcmVehCriteria 30}

-- 2.3.31 Vehicle ID 
dcmVehicleID OBJECT-TYPE
 SYNTAX  OCTET STRING (SIZE (0..32))
 ACCESS  not-accessible
 STATUS  optional
 DESCRIPTION
 "Indicates a vehicle ID, typically read from the vehicle using an AVI (Automatic Vehicle Identification) device such as a tag.  This object can only be used in the PVR Study Configuration Table.  Since it is not an Integer, it cannot be used in the Filter Configuration Table.
This is a multiple-occurrence object where the number of occurrences is equal to the number of vehicle ID's associated with this vehicle.  
A NULL shall be recorded for any vehicle IDs that cannot be determined.
When this object is used in a PVR study, the value shall be stored using BER encoding (TLV) since it is an Octet String."
::= {dcmVehCriteria 31}

-- 2.3.32 Vehicle Time Tag in 1000th Seconds
dcmVehicleTimeTag1000 OBJECT-TYPE
 SYNTAX  INTEGER (0..999)
 ACCESS  not-accessible
 STATUS  optional
 DESCRIPTION
 "The time expressed in 1000th of a second (milliseconds). This object is only used when a higher resolution than 1 sec is required for a vehicle time tag.  
This value is used in conjunction with the 'controller-localTime' object in that this counter rolls over every second.  The DCM device shall record this value with its highest resolution which may be less than 100th of a second."
::= {dcmVehCriteria 32}
-- 2.4 DEVICE SETUP NODE

--DCM Device Setup Node
dcmDeviceSetup OBJECT IDENTIFIER ::= {dcm 2}
-- This node is an identifier used to group all objects for configuring of the
-- device setup parameters that are common to data collection and monitoring 
-- devices.

-- 2.4.1 Unique Device ID 
dcmDeviceId OBJECT-TYPE
 SYNTAX  OCTET STRING (SIZE (0..16))
 ACCESS  read-write
 STATUS  optional
 DESCRIPTION
 "Indicates a user-assigned unique number or string of characters that identifies the overall DCM device.  This is not to be confused with the dcmSiteID object value."
::= {dcmDeviceSetup 1}

-- 2.4.2 Battery Voltage 
dcmBatteryVoltage OBJECT-TYPE
 SYNTAX  INTEGER (0..255)
 ACCESS  read-only
 STATUS  optional
 DESCRIPTION
 "Indicates the voltage of the battery at the time of the request. The value range shall be 00.0-25.5V in 0.1 increments."
::= {dcmDeviceSetup 2}

-- 2.4.3 Charging Current
dcmChargingCurrent OBJECT-TYPE
 SYNTAX  INTEGER(-100000..100000) 
 ACCESS  read-only
 STATUS  optional
 DESCRIPTION
 "Indicates the charging current in milliAmperes at the time of the request.  The value range shall be +/- 100000 mA in 1 mA increments."
::= {dcmDeviceSetup 3}

-- 2.4.4 Current Number Of IO Boards
dcmNumIoBoards OBJECT-TYPE
 SYNTAX  INTEGER(0..255) 
 ACCESS  read-only
 STATUS  optional
 DESCRIPTION
 "Indicates the current number of IO Boards configured in the dcmIOBoardConfigTable."
::= {dcmDeviceSetup 4}

-- 2.4.5 Maximum Number Of IO Board Configuration Table Rows
dcmIOBCTMaxNumRows OBJECT-TYPE
 SYNTAX DcmMaxNumRows
 ACCESS read-only
 STATUS mandatory
 DESCRIPTION
 "Indicates the maximum number of rows allowed for the IO Board Configuration Table."
::= {dcmDeviceSetup 5}

-- 2.4.6 Current Number Of IO Board Configuration Table Rows
dcmIOBCTCurNumRows OBJECT-TYPE
 SYNTAX DcmCurNumRows
 ACCESS read-only
 STATUS mandatory
 DESCRIPTION
 "Indicates the current number of rows existing in the IO Board Config Table."
::= {dcmDeviceSetup 6}

-- 2.4.7 IO Board Configuration Table 
dcmIOBoardConfigTable OBJECT-TYPE
 SYNTAX   SEQUENCE OF DcmIOBoardConfigEntry
 ACCESS   not-accessible
 STATUS   optional
 DESCRIPTION
 "This table defines the configuration parameters for each IO Board installed in the DCM device. Rows are created/deleted only through the insertion or removal of boards within the device.  There may be one or more entries for each IO board in the device (e.g. a single IO board may support multiple functions such as cpu and storageMedia).  This is a double-indexed table."
::= {dcmDeviceSetup 7}

dcmIOBoardConfigEntry OBJECT-TYPE
 SYNTAX   DcmIOBoardConfigEntry 
 ACCESS   not-accessible
 STATUS   mandatory
 DESCRIPTION "..."
 INDEX    {dcmIOBCBoardNum, dcmIOBoardFunction}
::= {dcmIOBoardConfigTable 1}

DcmIOBoardConfigEntry  ::= SEQUENCE 
{
 dcmIOBCBoardNum       DcmIOBoardNum,
 dcmIOBoardFunction    DcmIOBoardFtn,
 dcmIOBCNumIO          INTEGER,
 dcmIOBoardType        INTEGER,
 dcmIOBoardDescription OCTET STRING,
 dcmIOBoardStatus      INTEGER,
 dcmIOBoardControl     INTEGER
}

-- 2.4.7.1 IO Board Number
dcmIOBCBoardNum OBJECT-TYPE
 SYNTAX   DcmIOBoardNum
 ACCESS   read-only
 STATUS   mandatory
 DESCRIPTION
 "Indicates the first index into this table.  It represents a unique number for each IO Board that has been installed within the device.  This index is assigned by the device and must be sequential."
::= {dcmIOBoardConfigEntry 1}

-- 2.4.7.2 IO Board Function
dcmIOBoardFunction OBJECT-TYPE
 SYNTAX   DcmIOBoardFtn
 ACCESS   read-only
 STATUS   mandatory
 DESCRIPTION
 "Since an IO board can have multiple functions, this index allows the capability to define multiple IO Board Function Types for the same board. For instance a CPU board might have roadtube inputs and storage media available.  Although the IO Board Function Type could be used for the 2nd index, it would probably end up in a table that had non-sequential indexes.  This secondary index is assigned by the device and must be sequential."
::= {dcmIOBoardConfigEntry 2}

-- 2.4.7.3 IO Board Number Of IO
dcmIOBCNumIO OBJECT-TYPE
 SYNTAX   INTEGER (1..255)
 ACCESS   read-only
 STATUS   mandatory
 DESCRIPTION
 "This is the number of IO's of the type specified by IO Board Function Type for this board number specified by IO Board # in this row."
::= {dcmIOBoardConfigEntry 3}

-- 2.4.7.4 IO Board Function Type
dcmIOBoardType OBJECT-TYPE
 SYNTAX INTEGER 
 {
  other (1),
  cpu (2),
  storageMedia (3),
  inputNonSensor (4),
  output (5),
  comms (6),
  keyboard (7),
  display (8),
  roadTube (9),
  piezo (10),
  loop (11),
  wimPiezo (12),
  bendingPlate (13),
  contactClosure (14),
  acoustic (15),
  radar (16),
  microwave (17),
  infrared (18),
  laser (19),
  optoIsolated (20),
  fiberOptic (21),
  contactRelay (22),
  quartz (23),
  lightcurtain (24),
  video (25),
  timer (26),
  fiberOpticWim (27),
  ultrasound (28)
 }
 ACCESS   read-only
 STATUS   mandatory
 DESCRIPTION
 "Indicates the main functional type of this IO board.  The values are:
other – not defined below
cpu – main processor 
storageMedia – board provides data storage area (e.g. FLASH, SRAM, Hard Disk,…)
inputNonSensor – board provides input from a non-sensor (e.g. contact input controlled by an external software application)
output – board provides output functionality (e.g. solid state relay)
comms – board provides communications functionality (e.g. rs232, Ethernet,…)
keyboard - board provides key inputs
display – board provides display capability (e.g. LCD…)
roadTube – IO sensor
piezo – IO sensor
loop – IO sensor
wimPiezo – IO sensor
bendingPlate – IO sensor
contactClosure – IO sensor
acoustic – IO sensor
radar – IO sensor
microwave – IO sensor
infrared – IO sensor
laser – IO sensor
optoIsolated – IO sensor
fiberOptic – IO sensor
contactRelay – IO sensor
quartz – IO sensor
lightcurtain – IO sensor
video – IO sensor
timer – IO sensor
fiberOpticWim – IO sensor
ultrasound – IO sensor"
::= {dcmIOBoardConfigEntry 4}

-- 2.4.7.5 IO Board Description
dcmIOBoardDescription OBJECT-TYPE
 SYNTAX   OCTET STRING (SIZE (0..127))
 ACCESS   read-only
 STATUS   optional
 DESCRIPTION
 "Indicates a device-provided description of the board.  It is suggested that this string contain information such as board slot/address in device, firmware version, hardware version, model #, serial #, vendor name, # of IO ports on this board, storage media type (sram, flash,…), storage media size.  Note that all listed information may not be applicable to each type of IO board.  This object is only used to identify more information regarding the IO board. It is not used to configure the board.  Some of the information in this object may be dynamic."
::= {dcmIOBoardConfigEntry 5}

-- 2.4.7.6 IO Board Status
dcmIOBoardStatus OBJECT-TYPE
 SYNTAX INTEGER 
 {
  enabled (1),
  disabled (2),
  fault (3),
  resetting (4),
  suspended (5)
 }
 ACCESS   read-only
 STATUS   mandatory
 DESCRIPTION
 "indicates whether this IO Board is currently active.  The values are:
enabled (1) – the board is required for the current study configuration and is  in use.
disabled (2) – the board is required for the current study configuration but has been disabled.
fault (3), - At least one of the IO channels on this board is in fault. The dcmPhysicalLogicalMapTable can be interrogated to determine which specific channels are in fault.
resetting (4) – this indicates that the IO board is currently being reset.  After the reset has completed, it shall be modified to (enabled), (suspended) or (fault).
suspended (5) - the board has been disabled by the device because it is not required for the current study configuration."
::= {dcmIOBoardConfigEntry 6}

-- 2.4.7.7 IO Board Control
dcmIOBoardControl OBJECT-TYPE
 SYNTAX INTEGER 
 {
  notSupported (1),
  enable (2),
  disable (3),
  reset (4),
  suspend (5)
 }
 ACCESS   read-write
 STATUS   mandatory
 DESCRIPTION
 "Allows a user to enable, disable, reset, or suspend this IO Board. The value of this object represents the last user-selected control.  If this board is disabled or enabled, then any entry in the dcmPhysicalLogicalMapTable which corresponds to this board shall set the IO Status Entry in that table appropriately.  For example, a user may want to temporarily disable a sensor board to make it easier to debug which sensor inputs may be causing problems in the field.  If the requested operation is not supported by the specified IO board, this field shal be set to 'notSupported'.  Performing a reset of a storage media shall result in the formatting of that media."
::= {dcmIOBoardConfigEntry 7}

-- 2.4.8 Maximum Number Of Physical To Logical Mapping Table Rows
dcmPLMTMaxNumRows OBJECT-TYPE
 SYNTAX DcmMaxNumRows
 ACCESS read-only
 STATUS mandatory
 DESCRIPTION
 "Indicates the maximum number of rows allowed for the Physical To Logical Mapping Table."
::= {dcmDeviceSetup 8}

-- 2.4.9 Current Number Of Physical To Logical Table Rows
dcmPLMTCurNumRows OBJECT-TYPE
 SYNTAX DcmCurNumRows
 ACCESS read-only
 STATUS mandatory
 DESCRIPTION
 "Indicates the current number of rows existing in the Physical To Logical  Table."
::= {dcmDeviceSetup 9}

-- 2.4.10 Physical to Logical Mapping Table 
dcmPhysicalLogicalMapTable OBJECT-TYPE
 SYNTAX SEQUENCE OF DcmPhysicalLogicalMapEntry
 ACCESS   not-accessible
 STATUS   optional
 DESCRIPTION
 "This table maps a physical IO to a unique logical IO number.  The logical IO number will then be used as a reference by the other objects/tables within this mib to manipulate the physical IO.  This is a double-indexed table."
::= {dcmDeviceSetup 10}

dcmPhysicalLogicalMapEntry OBJECT-TYPE
 SYNTAX   DcmPhysicalLogicalMapEntry 
 ACCESS   not-accessible
 STATUS   mandatory
 DESCRIPTION "..."
 INDEX {dcmPLMIOBoardNum, dcmPhysicalIONumber}
::= {dcmPhysicalLogicalMapTable 1}

DcmPhysicalLogicalMapEntry  ::= SEQUENCE
{
 dcmPLMIOBoardNum            DcmIOBoardNum,
 dcmPLMIOBoardFunction       DcmIOBoardFtn,
 dcmPhysicalIONumber         INTEGER,
 dcmPLMLogIONum              DcmLogIONum,
 dcmPhysicalLogicalIOStatus  INTEGER,
 dcmPhysicalLogicalIOControl INTEGER
}

-- 2.4.10.1 IO Board Number
dcmPLMIOBoardNum OBJECT-TYPE
 SYNTAX   DcmIOBoardNum
 ACCESS   read-only
 STATUS   mandatory
 DESCRIPTION
 "Indicates the first index into this table. Refer to DcmIOBoardNum for a more detailed description."
::= {dcmPhysicalLogicalMapEntry 1}
-- 2.4.10.2 
-- 2.4.10.3 IO Board Function
dcmPLMIOBoardFunction OBJECT-TYPE
 SYNTAX   DcmIOBoardFtn
 ACCESS   read-only
 STATUS   mandatory
 DESCRIPTION
 "Since an IO board can have multiple functions, this index identifies the function of the IO within the IO Board Number specified by dcmPLMIOBoardNum for this row."
::= {dcmPhysicalLogicalMapEntry 2}

-- 2.4.10.4 Physical IO Number
dcmPhysicalIONumber OBJECT-TYPE
 SYNTAX   INTEGER (1..255)
 ACCESS   read-only
 STATUS   mandatory
 DESCRIPTION
 "Indicates the second index into this table.  This index refers to a channel within an IO board (e.g. IO board 1 may have 4 inputs which would result in 4 entries in this table to map each of the 4 inputs 1-1, 1-2, 1-3, 1-4). This index is assigned by the device and must be sequential."
::= {dcmPhysicalLogicalMapEntry 3}

-- 2.4.10.5 Logical IO Number
dcmPLMLogIONum OBJECT-TYPE
 SYNTAX   DcmLogIONum 
 ACCESS   read-only
 STATUS   mandatory
 DESCRIPTION
 "See DcmLogIONum description"
::= {dcmPhysicalLogicalMapEntry 4}

-- 2.4.10.6 Physical IO Status
dcmPhysicalLogicalIOStatus OBJECT-TYPE
 SYNTAX INTEGER 
 {
  enabled (1),
  disabled (2),
  fault (3),
  resetting (4),
  suspended (5)
 }
 ACCESS   read-only
 STATUS   mandatory
 DESCRIPTION
 "Indicates the current status for this IO channel. The values are:
- enabled (1) – the IO is required by the current study configuration and is in use.
- disabled (2) – the IO is required for the current study configuration but has been disabled.
- fault (3), - This IO channel is in fault. 
- resetting (4) – this indicates that the IO is currently being reset.  After the reset has completed, it shall be modified to (enabled), (suspended) or (fault).
- suspended (5) – the IO has been disabled by the device because it is not required for the current study configuration."
::= {dcmPhysicalLogicalMapEntry 5}

-- 2.4.10.7 Physical IO Control
dcmPhysicalLogicalIOControl OBJECT-TYPE
 SYNTAX   INTEGER 
 {
  notSupported (1),
  enable (2),
  disable (3),
  reset (4),
  suspend (5)
 }
 ACCESS   read-write
 STATUS   mandatory
 DESCRIPTION
 "Allows an application to enable, disable,reset or suspend a physical IO channel.  The value of this object represents the last user-selected control.  An application may want to enable/disable an IO channel for diagnostic purposes.  If the requested operation is not supported by the specified IO channel, this value shall be set to 'notSupported'."
::= {dcmPhysicalLogicalMapEntry 6}

-- 2.4.11 Maximum Number Of Logical IO Parmater Table Rows
dcmLIOPTMaxNumRows OBJECT-TYPE
 SYNTAX DcmMaxNumRows
 ACCESS read-only
 STATUS mandatory
 DESCRIPTION
 "Indicates the maximum number of rows allowed for the Logical IO Parameter Table."
::= {dcmDeviceSetup 11}

-- 2.4.12 Current Number Of Logical IO Parameter Table Rows
dcmLIOPTCurNumRows OBJECT-TYPE
 SYNTAX DcmCurNumRows
 ACCESS read-only
 STATUS mandatory
 DESCRIPTION
 "Indicates the current number of rows existing in the Logical IO Parameter  Table."
::= {dcmDeviceSetup 12}

-- 2.4.13 Logical IO Parameter Table 
dcmIOParamTable OBJECT-TYPE
 SYNTAX   SEQUENCE OF DcmIOParamEntry
 ACCESS   not-accessible
 STATUS   optional
 DESCRIPTION	
 "This table defines parameters that can be applied to each IO channel to allow processing and adjustment of that IO channel.  There can be multiple rows within this table for each logical IO.  The indexing of this table will not be sequential.  If an application tries to define more rows than the device will allow, an application error code of 'exceeded max number of rows allowed' shall be set.  This is a double-indexed table.  The table can be managed thru dcmIOParamRowAdmin object.
If an attempt is made to set a parameter of an IO channel and the IO board associated with the IO channel can only set the parameter at a board level, all IO channels of that type (which have been entered into this table) on that IO board will be set to the specified value.  It is up to the application to re-read this table to determine if any of the requested parameters have been changed.    

Conversely, if it is possible to access each IO channel within a board then each IO channel has to be set individually.  Note that all IO channels may not require any parameters set and some IO channels may require multiple parameters set."
::= {dcmDeviceSetup 13}

dcmIOParamEntry OBJECT-TYPE
 SYNTAX   DcmIOParamEntry 
 ACCESS   not-accessible
 STATUS   mandatory
 DESCRIPTION "..."
 INDEX   {dcmIOPNum, dcmIOPTyp}
::= {dcmIOParamTable 1}

DcmIOParamEntry  ::= SEQUENCE 
{
 dcmIOPNum          DcmLogIONum,
 dcmIOPTyp          DcmIOParamType,
 dcmIOPVal          DcmIOParamValue,
 dcmIOParamRowAdmin DcmRowStatus
}

-- 2.4.13.1 IO Parameter Logical IO Number
dcmIOPNum OBJECT-TYPE
 SYNTAX   DcmLogIONum
 ACCESS   read-only
 STATUS   mandatory
 DESCRIPTION
 "First index into this table.  Refer to DcmLogIONum for detailed description."
::= {dcmIOParamEntry 1}
-- 2.4.13.2 
-- 2.4.13.3 IO Parameter Type 
dcmIOPTyp OBJECT-TYPE
 SYNTAX DcmIOParamType
 ACCESS   read-only
 STATUS   mandatory
 DESCRIPTION
 "Indicates the second index into this table.  A second index is required to allow assigning multiple parameters for any IO channel. The indexes will most likely not be assigned sequentially.  If an application tries to set a parameter on an IO channel that is invalid, an application error of 'invalid option' shall be set."
::= {dcmIOParamEntry 2}

-- 2.4.13.4 IO Parameter Value
dcmIOPVal OBJECT-TYPE
 SYNTAX   DcmIOParamValue
 ACCESS   read-write
 STATUS   mandatory
 DESCRIPTION
 "Indicates the value for the selected IO parameter. Refer to DcmIOParamValue a detailed description of the allowed values."
::= {dcmIOParamEntry 3}

-- 2.4.13.5 IO Parameter Row Admin
dcmIOParamRowAdmin OBJECT-TYPE
 SYNTAX   DcmRowStatus 
 ACCESS   read-write
 STATUS   mandatory
 DESCRIPTION
 "Allows management of the associated 'logical IO/parameter combination' (this row of this table).  The SYNTAX definition allows to create, delete, disable, or edit the row."
::= {dcmIOParamEntry 4}

-- 2.5 OPERATING STATUS CONFIGURATION NODE
--DCM Operating Status Configuration Node
dcmOpsStatus OBJECT IDENTIFIER ::= {dcm 3}
-- This node is an identifier used to group all objects indicating the 
-- operating status in ways that are common to data collection and 
-- monitoring devices.

-- objects addressing current date and current time are defined in NTCIP 1201 
--(plus amendment 1, which are referenced in Annex A.

-- 2.5.1 dcm Resets
dcmReset OBJECT-TYPE
 SYNTAX  INTEGER
 {
  other (1),
  hardReset (2), 
  softReset (3), 
  commReset (4), 
  factoryReset (5), 
  userReset (6), 
  tableClear (7)  
 }
 ACCESS  read-write
 STATUS  optional
 DESCRIPTION
 "indicates the different types of resets that may be issued to the dcm device.  The values and their meaning are: 
1=Other
2=Hard Reset  
- (restart program, reset comms, clear all user settings, reset sensor boards, reset keyboard/display, reset cpu program memory, does not clear data files, resets to all factory defaults, stops current recording study)
3=Soft Reset
- (restart program, does not reset comms, does not change user settings, does not reset sensor boards, resets keyboard/display, resets cpu program memory, does not clear data files, does not reset to factory defaults, stops  current recording study)
4=Comms Reset
- Resets the comms channel used to communicate with the field unit to user defaults.
- It is recommended that all required elements are resynched by the dcm device to ensure that communications is not lost with the dcm unit (e.g. modem).
5=Factory Reset 
- User settings consist of all structures that can be written to.
- Resets all user settings to factory defaults.
6=User Reset 
- Which objects/tables to reset and the values to reset them to is  configured by the dcmURCTTable
7=Table Clear 
- The clear operation is based on the dcmTableClearTable
"
::= {dcmOpsStatus 1}

-- 2.5.2 Maximum Number Of Table Clear Table Rows
dcmTCTMaxNumRows OBJECT-TYPE
 SYNTAX DcmMaxNumRows
 ACCESS read-only
 STATUS mandatory
 DESCRIPTION
 "Indicates the maximum number of rows allowed for the Table Clear Table."
::= {dcmOpsStatus 2}

-- 2.5.3 Current Number Of Table Clear Table Rows
dcmTCTCurNumRows OBJECT-TYPE
 SYNTAX DcmCurNumRows
 ACCESS read-only
 STATUS mandatory
 DESCRIPTION
 "Indicates the current number of rows existing in the Table Clear Table."
::= {dcmOpsStatus 3}

-- 2.5.4 Table Clear Table
dcmTableClearTable OBJECT-TYPE
 SYNTAX  SEQUENCE OF DcmTableClearEntry
 ACCESS  not-accessible
 STATUS  optional
 DESCRIPTION
"This table indicates which tables to perform a clear on.  Multiple tables or multiple rows within a table can be specified to be cleared by configuring multiple rows within this table.  The clear can be defined to clear the whole table or just a row within the table. This is a singly-indexed table.  All entries must be sequentially indexed.  The OID of this table shall not be allowed as a valid OID entry in this table."
::= {dcmOpsStatus 4}

dcmTableClearEntry OBJECT-TYPE	
 SYNTAX DcmTableClearEntry
 ACCESS not-accessible
 STATUS mandatory
 DESCRIPTION "..."
 INDEX {dcmTableClearIndex}
::={dcmTableClearTable 1}

DcmTableClearEntry ::= SEQUENCE 
{
 dcmTableClearIndex INTEGER, 
 dcmTCTOID          OBJECT IDENTIFIER,
 dcmTCTAction       INTEGER, 
 dcmTCTRowAdmin     DcmRowStatus  
}

-- 2.5.4.1 Table Clear Index
dcmTableClearIndex OBJECT-TYPE
 SYNTAX INTEGER (1..255)
 ACCESS read-only
 STATUS mandatory
 DESCRIPTION
 "indicates the only index into this table."
::= {dcmTableClearEntry 1}

-- 2.5.4.2 Table Clear Object Identifier
dcmTCTOID OBJECT-TYPE
 SYNTAX OBJECT IDENTIFIER
 ACCESS read-write
 STATUS mandatory
 DESCRIPTION
 "this value points to the OID of a table.  The value of the next object (dcmTCTAction) then points to the rows that are to be cleared.  An error (noSuchName) shall be returned, if the OID pointed to within this object instance is not supported by the device."
::= {dcmTableClearEntry 2}

-- 2.5.4.3 Table Clear Action
dcmTCTAction OBJECT-TYPE
 SYNTAX INTEGER (0..255)
 ACCESS read-write
 STATUS mandatory
 DESCRIPTION
 "Setting this to zero (0) shall remove the whole table specified by dcmTCTOID.  Any other value refers to the row number (relative to the first index of the specified table) to clear.  (e.g. if doubly-indexed table, 1-1,1-2,2-1,2-2, setting this to a 2 would clear out all rows with the first index=2, 2-1 and 2-2).  This action will occur when the dcmReset object is set to tableClear.  If the row or table can not be deleted, then the row or table shall go to factory default settings.  If removing the row or table will result in an invalid device configuration, the device shall return an error and not perform the requested action."
::= {dcmTableClearEntry 3}

-- 2.5.4.4 Table Clear Row Admin
dcmTCTRowAdmin OBJECT-TYPE
 SYNTAX   DcmRowStatus 
 ACCESS   read-write
 STATUS   mandatory
 DESCRIPTION
 "Allows management of this row of this table.  The SYNTAX definition allows to create, delete, disable, or edit the row."
::= {dcmTableClearEntry 4}

-- 2.5.5 Current Number Of User Configuration Settings
dcmNumUserConfigs OBJECT-TYPE
 SYNTAX  INTEGER(0..255) 
 ACCESS  read-only
 STATUS  optional
 DESCRIPTION
 "Indicates the current number of objects configured for a user reset.  Objects can be configured for a User Reset through the User Reset Config Table (dcmURCTTable).  Note that this is different than the Current Number of User Reset Config Table Rows object.  For example a user may configure two rows (two objects) in the User Reset Config Table and then configure 1 more row (one object) in the User Reset Config Table.  The dcmNumUserConfigs object will indicate that three objects have been configured for a User Reset, but the Current Number of User Reset Config Table Rows will only indicate one as the most recent value (since only one row in the User Reset Config table would be currently configured)."
::= {dcmOpsStatus 5}

-- 2.5.6 Maximum Number Of User Reset Config Table Rows
dcmURCTMaxNumRows OBJECT-TYPE
 SYNTAX DcmMaxNumRows
 ACCESS read-only
 STATUS mandatory
 DESCRIPTION
 "Indicates the maximum number of rows allowed for the User Reset Config Table."
::= {dcmOpsStatus 6}

-- 2.5.7 Current Number Of User Reset Config Table Rows
dcmURCTCurNumRows OBJECT-TYPE
 SYNTAX DcmCurNumRows
 ACCESS read-only
 STATUS mandatory
 DESCRIPTION
 "Indicates the current number of rows existing in the User Reset Config Table."
::= {dcmOpsStatus 7}

-- 2.5.8 User Reset Config Table
dcmURCTTable OBJECT-TYPE
 SYNTAX  SEQUENCE OF DcmURCTEntry
 ACCESS  not-accessible
 STATUS  optional
 DESCRIPTION "Allows a user to define the current settings of an existing structure to be used as User Default settings for a User Reset.  Multiple structures can be saved as user defaults by specifying multiple row entries in this table (or each structure can be saved as a user default one at a time (only specifying one row in this table)).  The OID of this table shall not be allowed as a valid OID entry in this table. This table has a single index. The index must be assigned sequentially by the device."
::= {dcmOpsStatus 8}

dcmURCTEntry OBJECT-TYPE
 SYNTAX DcmURCTEntry
 ACCESS not-accessible
 STATUS mandatory
 DESCRIPTION "..."
 INDEX {dcmUserResetConfigIndex}
::={dcmURCTTable 1}

DcmURCTEntry ::= SEQUENCE 
{
 dcmUserResetConfigIndex INTEGER, 
 dcmURCTOID              OBJECT IDENTIFIER, 
 dcmURCTAction           INTEGER, 
 dcmURCTRowAdmin         DcmRowStatus  
}

-- 2.5.8.1 User Reset Configuration Index
dcmUserResetConfigIndex OBJECT-TYPE
 SYNTAX INTEGER (1..255)
 ACCESS read-only
 STATUS mandatory
 DESCRIPTION
 "indicates the only index into this table."
::= {dcmURCTEntry 1}

-- 2.5.8.2 User Reset Table Object Identifier
dcmURCTOID OBJECT-TYPE
 SYNTAX OBJECT IDENTIFIER
 ACCESS read-write
 STATUS mandatory
 DESCRIPTION
 "this value points to an OID, which may be a leaf OID or a table OID.  The value of the next object (dcmURCTAction) then points to the action that is to be performed on the referenced OID.  An error of (noSuchName) shall be returned, if the OID pointed to is not supported by the device."
::= {dcmURCTEntry 2}

-- 2.5.8.3 User Reset Config Table Action
dcmURCTAction OBJECT-TYPE
 SYNTAX INTEGER 
 {
  clearAllUserDefaults (1),
  clearUserDefsFromOID (2),
  saveUserDefsFromOID (3)
 }
 ACCESS read-write
 STATUS mandatory
 DESCRIPTION
 "Setting this to one (1) shall remove all previously-defined user reset settings (it ignores the setting of dcmURCTOID).  
Setting this to two (2) shall remove only the structure referenced by dcmURCTOID from the user reset settings defaults.  
Setting this to three (3) shall save the current settings of the structure referenced by dcmURCTOID as a user reset setting default for that structure.  

The only way to read what the user settings have been set to is to perform a User Reset.  It is left up to the controlling application to keep track of what has been configured as User Default Settings. The OID of this table can be added to the 'Object Change ID Table' to allow tracking if the User Default Settings have been modified."
::= {dcmURCTEntry 3}

-- 2.5.8.4 User Reset Config Row Admin
dcmURCTRowAdmin OBJECT-TYPE
 SYNTAX   DcmRowStatus 
 ACCESS   read-write
 STATUS   mandatory
 DESCRIPTION
 "Allows management of this row of this table.  The SYNTAX definition allows to create, delete, disable, or edit the row."
::= {dcmURCTEntry 4}

-- 2.5.9 Maximum Number Of Object Change ID Table Rows
dcmOCIDTMaxNumRows OBJECT-TYPE
 SYNTAX DcmMaxNumRows
 ACCESS read-only
 STATUS mandatory
 DESCRIPTION
 "Indicates the maximum number of rows allowed for the Object Change ID Table."
::= {dcmOpsStatus 9}

-- 2.5.10 Current Number Of Object Change ID Table Rows
dcmOCIDTCurNumRows OBJECT-TYPE
 SYNTAX DcmCurNumRows
 ACCESS read-only
 STATUS mandatory
 DESCRIPTION
 "Indicates the current number of rows existing in the Object Change ID Table."
::= {dcmOpsStatus 10}

-- 2.5.11 Object Change ID Table 
dcmOCITable OBJECT-TYPE
 SYNTAX SEQUENCE OF DcmOCIEntry
 ACCESS not-accessible
 STATUS optional
 DESCRIPTION
 "This table allows a user to configure which objects to monitor.  The row entry is updated by the device if the parameter value of the referenced object or the value of any of the objects 'below' the referenced object node have changed. It is used to give an external application visibility that some configuration objects have changed.  This table has a single index. The index must be assigned sequentially by the device."
::= {dcmOpsStatus 11}

dcmOCIEntry OBJECT-TYPE
 SYNTAX   DcmOCIEntry 
 ACCESS   not-accessible
 STATUS   mandatory
 DESCRIPTION "..."
 INDEX    {dcmOCIdIndex}
::= {dcmOCITable 1}
	
DcmOCIEntry  ::= SEQUENCE 
{
 dcmOCIdIndex      INTEGER,
 dcmOCIdOID	       OBJECT IDENTIFIER,
 dcmOCIdTime       Counter,
 dcmOCIdRowAdmin   DcmRowStatus
}

-- 2.5.11.1 Object Change ID Table Index
dcmOCIdIndex OBJECT-TYPE
 SYNTAX INTEGER (1..255)
 ACCESS read-only
 STATUS mandatory
 DESCRIPTION
 "Indicates the general index into this table.  The values must be assigned sequentially."
::= {dcmOCIEntry 1}

-- 2.5.11.2 Object Change ID Table OID
dcmOCIdOID OBJECT-TYPE
 SYNTAX OBJECT IDENTIFIER
 ACCESS read-write
 STATUS mandatory
 DESCRIPTION
 "Indicates the Object OID that is being monitored.  The referenced OID can be any OID supported by the device."
::= {dcmOCIEntry 2}

-- 2.5.11.3 Object Change ID Table Time
dcmOCIdTime OBJECT-TYPE
 SYNTAX  Counter
 ACCESS  read-only
 STATUS  mandatory
 DESCRIPTION
 "Indicates the timestamp associated with the dcmOCIdIndex (this row).  The value shows when the change to the reference object/object node occurred.  The setup of this value is the same as defined for the controller-localTime object as defined in NTCIP 1201."
::= {dcmOCIEntry 3}

-- 2.5.11.4 Object Change ID Row Admin
dcmOCIdRowAdmin OBJECT-TYPE
 SYNTAX   DcmRowStatus 
 ACCESS   read-write
 STATUS   mandatory
 DESCRIPTION
 "Allows management of the associated row of this table.  The SYNTAX definition allows to create, delete, disable, or edit the row."
::= {dcmOCIEntry 4}


-- 2.6 SITE SETUP NODE
--DCM Site Setup Node
dcmSiteSetup OBJECT IDENTIFIER ::= {dcm 4}
-- This node is an identifier used to group all objects for configuring 
-- a data collection site that are common to data collection and 
-- monitoring devices.

-- 2.6.1 Unique Site ID
dcmSiteId OBJECT-TYPE
 SYNTAX  OCTET STRING (SIZE (0..40))
 ACCESS  read-write
 STATUS  optional
 DESCRIPTION
 "Indicates a user-assigned unique number or string of characters that identifies the location of the DCM device.  Typically, agencies will use character positions within this field to denote things such as county, city, lane, direction.  This is not to be confused with the unique device ID (see dcmDeviceID)."
::= {dcmSiteSetup 1}

-- 2.6.2 Maximum Length of Site Description
dcmMaxLengthSiteDescr OBJECT-TYPE
 SYNTAX  INTEGER (0..255)
 ACCESS  read-only
 STATUS  optional
 DESCRIPTION
 "indicates the number of characters that are available within this dcm device to express the site description."
::= {dcmSiteSetup 2}

-- 2.6.3 Site Description
dcmSiteDescription OBJECT-TYPE
 SYNTAX  OCTET STRING (SIZE (0..127))
 ACCESS  read-write 
 STATUS  optional
 DESCRIPTION
 " text description of the site at which the dcm device is currently placed."
::= {dcmSiteSetup 3}

-- 2.6.4 Maximum Number of Sensors per Array
dcmMaxSensorsPerArray   OBJECT-TYPE
 SYNTAX  INTEGER (0..255)
 ACCESS  read-only
 STATUS  optional
 DESCRIPTION
 "indicates the maximum number of all types of sensors that can be utilized per defined array.  A typical DCM device will support between 1 to 4 sensors per array."
::= {dcmSiteSetup 4}

-- 2.6.5 Maximum Number of Arrays 
dcmMaxNumArrays OBJECT-TYPE
 SYNTAX  INTEGER (1..255)
 ACCESS  read-only
 STATUS  optional
 DESCRIPTION
 "indicates the maximum number of arrays that can be defined within this device.  A typical DCM device will support between 4 and 16 arrays.  The number of arrays that can be defined will also be limited by the amount of IO fitted in the board.  (e.g. the device may have a max of 16 arrays, but if only 8 loop inputs are present in the device, then only 4 arrays of loop loop can be configured)."
::= {dcmSiteSetup 5}

-- 2.6.6 Current Number Of Arrays
dcmNumArrays   OBJECT-TYPE
 SYNTAX  INTEGER (0..255)
 ACCESS  read-only
 STATUS  optional
 DESCRIPTION
 "indicates the current number of defined arrays within this DCM device.  The value of this object shall not exceed the value of the dcmMaxNumArrays object."
::= {dcmSiteSetup 6}

-- 2.6.7 Maximum Number Of Logical IO To Array Mapping Table Rows
dcmLIOMTMaxNumRows OBJECT-TYPE
 SYNTAX DcmMaxNumRows
 ACCESS read-only
 STATUS mandatory
 DESCRIPTION
 "Indicates the maximum number of rows allowed for the Logical IO To Array Mapping Table."
::= {dcmSiteSetup 7}

-- 2.6.8 Current Number Of Logical IO To Array Mapping Table Rows
dcmLIOMTCurNumRows OBJECT-TYPE
 SYNTAX DcmCurNumRows
 ACCESS read-only
 STATUS mandatory
 DESCRIPTION
 "Indicates the current number of rows existing in the Logical IO To Array Mapping Table."
::= {dcmSiteSetup 8}

-- 2.6.9 Logical IO To Array Mapping Table 
dcmLogicalIOArrayMapTable OBJECT-TYPE
 SYNTAX   SEQUENCE OF DcmLogicalIOArrayMapEntry
 ACCESS   not-accessible
 STATUS   optional
 DESCRIPTION
 "This table assigns logical IO's from the Physical to Logical IO Mapping  Table to an array. This is a double-indexed table.  Since the logical IO number is used as the 2nd index into this table, it will most likely not be sequential.  The table can be managed by the dcmLogicalIOArrayMapRowAdmin object."
::= {dcmSiteSetup 9}

dcmLogicalIOArrayMapEntry OBJECT-TYPE
 SYNTAX   DcmLogicalIOArrayMapEntry 
 ACCESS   not-accessible
 STATUS   mandatory
 DESCRIPTION "..."
 INDEX  {dcmIOAMArrNum, dcmIOAMIONum}
::= {dcmLogicalIOArrayMapTable 1}

DcmLogicalIOArrayMapEntry  ::= SEQUENCE 
{
 dcmIOAMArrNum			DcmArrayNum,
 dcmIOAMIONum                 DcmLogIONum,
 dcmIOSpacing			INTEGER,
 dcmIOPosition			INTEGER,
 dcmIOFunctionality		INTEGER,
 dcmLogicalIOArrayMapRowAdmin	DcmRowStatus
}

-- 2.6.9.1 Array Number
dcmIOAMArrNum OBJECT-TYPE
 SYNTAX   DcmArrayNum
 ACCESS   read-only
 STATUS   mandatory
 DESCRIPTION
 "Indicates the first index into this table.  Refer to DcmArrayNum for more a detailed description."
::= {dcmLogicalIOArrayMapEntry 1}

-- 2.6.9.2 Logical IO Number
dcmIOAMIONum OBJECT-TYPE
 SYNTAX DcmLogIONum
 ACCESS read-only
 STATUS mandatory
 DESCRIPTION
 "Refer to DcmLogIONum for description."
::= {dcmLogicalIOArrayMapEntry 2}


-- 2.6.9.3 IO Spacing
dcmIOSpacing OBJECT-TYPE
 SYNTAX   INTEGER (0..65535)
 ACCESS   read-write
 STATUS   mandatory
 DESCRIPTION
 "Indicates the spacing between each sensor associated with the same array number (same value of dcmIOAMArrNum).
A value of zero (0) indicates that the specified sensor is the first sensor in the array.  It may also be the only sensor in the array.  There shall always be at least one logical IO associated with an array.  There could also be multiple IO's associate with an array (multiple rows in this table)A non-zero value indicates the distance from the front edge of the first sensor (travel direction) to the front edge of the sensor defined in this row of this table."
--UNIT      millimeter
::= {dcmLogicalIOArrayMapEntry 3}

-- 2.6.9.4 IO Position
dcmIOPosition OBJECT-TYPE
 SYNTAX   INTEGER 
 {
  other (1),
  full (2),
  center (3),
  multiple (4),
  leftHalf (5),
  rightHalf (6),
  leftThird (7),
  centerThird (8),
  rightThird (9),
  above (10),
  below (11),
  sidefire (12),
  wheelPath (13),
  negWheelPath (14)
 }
 ACCESS   read-write
 STATUS   mandatory
 DESCRIPTION
 "indicates the position of a sensor within an array relative to the lane(s) of travel. The values are:
- other (1),= not defined below.
- full (2),= sensor covers entire lane
- center (3),= sensor is located in the center of the lane, but doesn't cover the entire lane
- multiple (4),= sensor crosses multiple lanes
- leftHalf (5),= sensor is located in the left (left sensor relative to the direction of travel) half of the lane
- rightHalf (6),= sensor is located in the right (right sensor relative to the direction of travel) half of the lane
- leftThird (7),= sensor is located in the left third of the lane (left sensor relative to the direction of travel)
- centerThird (8),= sensor is located in the center third of the lane
- rightThird (9),= sensor is located in the right third of the lane (right sensor relative to the direction of travel)
- above (10),= sensor is located above the lane
- below (11),= sensor is located below the lane
- sidefire (12)= sensor is located perpendicular to the lane
- wheelPath (13)= sensor is located in the wheel path of the lane
- negWheelPath (14)= sensor is located outside of the wheel path in the lane"
::= {dcmLogicalIOArrayMapEntry 4}

-- 2.6.9.5 IO Functionality
dcmIOFunctionality OBJECT-TYPE
 SYNTAX   INTEGER 
 {
  other (1),
  vehiclePresence (2),
  axle (3),
  wimAxle (4),
  temperature (5),
  negativeAxle (6),
  onScale (7),
  offScale (8),
  overheight (9),
  avi (10),
  height (11),
  width (12)
 }
 ACCESS   read-write
 STATUS   mandatory
 DESCRIPTION
 " Indicates the generic functionality for the specified logical IO.  The values are:
- other (1),= not defined below.
- vehiclePresence (2),= the IO can detect the presence of vehicles (e.g. loop)
- axle (3),=  the IO can only detect axle strikes (e.g. roadtube)
- wimAxle (4),= the IO is used to determine the weight of an axle (e.g. class 1 piezo)
- temperature (5),= the IO is used to measure temperature
- negativeAxle (6),= the IO is used to subtract out axles (e.g. short long roadtube configuration)
- onScale (7),= the IO is used to determine if vehicles are tracking in a consistent position within the lane
- offScale (8),= the IO is used to determine if vehicles are not tracking in a consistent position within the lane
- overheight (9),= the IO is used to determine if the overall height of a vehicle exceeds a maximum height
- avi (10), = Automatic Vehicle Identifier, the IO is used to uniquely identify a vehicle
- height (11), = the IO is used to measure vehicle height
- width (12), = the IO is used to measure vehicle width"
::= {dcmLogicalIOArrayMapEntry 5}

-- 2.6.9.6 IO Row Administration
dcmLogicalIOArrayMapRowAdmin OBJECT-TYPE
 SYNTAX   DcmRowStatus 
 ACCESS   read-write
 STATUS   optional
 DESCRIPTION
 "allows management of the arrays (this row of this table).  The SYNTAX definition allows to create, delete, disable, or edit a row."
::= {dcmLogicalIOArrayMapEntry 6}

-- 2.6.10 Maximum Number of Calibration Factors per Array
dcmMaxCalFactorsPerArray   OBJECT-TYPE
 SYNTAX  INTEGER (0..255)
 ACCESS  read-only
 STATUS  optional
 DESCRIPTION
 "indicates the maximum number of calibration factors that can be utilized per defined array.  A typical DCM device will support between 1 to 3 calibration factors per array."
::= {dcmSiteSetup 10}

-- 2.6.11 Maximum Number Of Array Parameter Table Rows
dcmAPTMaxNumRows OBJECT-TYPE
 SYNTAX DcmMaxNumRows
 ACCESS read-only
 STATUS mandatory
 DESCRIPTION
 "Indicates the maximum number of rows allowed for the Array Parameter Table."
::= {dcmSiteSetup 11}

-- 2.6.12 Current Number Of Array Parameter Table Rows
dcmAPTCurNumRows OBJECT-TYPE
 SYNTAX DcmCurNumRows
 ACCESS read-only
 STATUS mandatory
 DESCRIPTION
 "Indicates the current number of rows existing in the Array Parameter Table."
::= {dcmSiteSetup 12}

-- 2.6.13 Array Parameter Table 
dcmArrayParameterTable OBJECT-TYPE
 SYNTAX   SEQUENCE OF DcmArrayParameterEntry
 ACCESS   not-accessible
 STATUS   optional
 DESCRIPTION
 " This table assigns parameters to arrays (typically for the purposes of fine-tuning the processing of the array within the dcm device.).  This is a double-indexed table.  Since the Array Parameter Type is used as the 2nd index, it will most likely not be sequential.  The table can be managed dcmArrayParameterRowAdmin object. "
::= {dcmSiteSetup 13}

dcmArrayParameterEntry OBJECT-TYPE
 SYNTAX   DcmArrayParameterEntry 
 ACCESS   not-accessible
 STATUS   mandatory
 DESCRIPTION "..."
 INDEX    {dcmAPArrNum, dcmAPType}
::= {dcmArrayParameterTable 1}

DcmArrayParameterEntry ::= SEQUENCE 
{
 dcmAPArrNum               DcmArrayNum,
 dcmAPType                 DcmArrayParamType,
 dcmAPValue                DcmArrayParamValue,
 dcmAPFileName             DcmArrayParamFileName,
 dcmArrayParameterRowAdmin DcmRowStatus
}

-- 2.6.13.1 Array Number
dcmAPArrNum OBJECT-TYPE
 SYNTAX DcmArrayNum
 ACCESS   read-only
 STATUS   mandatory
 DESCRIPTION
 "Indicates the first index into this table.  Refer to DcmArrayNum for a more detailed description."
::= {dcmArrayParameterEntry 1}

-- 2.6.13.2 Array Parameter Type
dcmAPType OBJECT-TYPE
 SYNTAX DcmArrayParamType
 ACCESS   read-only
 STATUS   mandatory
 DESCRIPTION
 "Indicates the type of parameter associated with an array. One or more types can be associated with an array.  
Refer to DcmArrayParamType for a more detailed description."
::= {dcmArrayParameterEntry 2}

-- 2.6.13.3 Array Parameter Value
dcmAPValue OBJECT-TYPE
 SYNTAX   DcmArrayParamValue
 ACCESS   read-write
 STATUS   mandatory
 DESCRIPTION
 "Indicates the value associated with a particular array parameter type as specified by the dcmAPType column.  Refer to DcmArrayParamValue for a more detailed description."
::= {dcmArrayParameterEntry 3}

-- 2.6.13.4 Array Parameter FileName Pointer
dcmAPFileName OBJECT-TYPE
 SYNTAX   DcmArrayParamFileName
 ACCESS   read-write
 STATUS   mandatory
 DESCRIPTION
 "Indicates a file name that contains the array parameter calibration information. Refer to DcmArrayParamFileName for a more detailed description."
::= {dcmArrayParameterEntry 4}

-- 2.6.13.5 Array Parameter Table Row Administration
dcmArrayParameterRowAdmin OBJECT-TYPE
 SYNTAX   DcmRowStatus 
 ACCESS   read-write
 STATUS   mandatory
 DESCRIPTION
 "allows management of the array parameters (this row of this table).  The SYNTAX definition allows to create, delete, disable, or edit a row."
::= {dcmArrayParameterEntry 5}

-- 2.6.14 Maximum Number Of Array Speed Calibration Table Rows
dcmASCTMaxNumRows OBJECT-TYPE
 SYNTAX DcmMaxNumRows
 ACCESS read-only
 STATUS mandatory
 DESCRIPTION
 "Indicates the maximum number of rows allowed for the Array Speed Calibration Table."
::= {dcmSiteSetup 14}

-- 2.6.15 Current Number Of Array Speed Calibration Table Rows
dcmASCTCurNumRows OBJECT-TYPE
 SYNTAX DcmCurNumRows
 ACCESS read-only
 STATUS mandatory
 DESCRIPTION
 "Indicates the current number of rows existing in the Array Speed Calibration Table."
::= {dcmSiteSetup 15}

-- 2.6.16 Array Speed Calibration Table 
dcmArraySpeedCalibrationTable OBJECT-TYPE
 SYNTAX   SEQUENCE OF DcmArraySpeedCalibrationEntry
 ACCESS   not-accessible
 STATUS   optional
 DESCRIPTION
 "This table is a triple-indexed table.  It defines the calibration factors that are used to calibrate a speed algorithm. Historically speed was calibrated by adjusting sensor spacings within an array. This table allows for the spacings to remain fixed at the actual values.  The table can be managed thru the dcmArraySpeedCalibrationRowAdmin object."
::= {dcmSiteSetup 16}

dcmArraySpeedCalibrationEntry OBJECT-TYPE
 SYNTAX   DcmArraySpeedCalibrationEntry 
 ACCESS   not-accessible
 STATUS   mandatory
 DESCRIPTION "..."
 INDEX    {dcmASCArrNum, dcmLogicalIONumber1, dcmLogicalIONumber2}
::= {dcmArraySpeedCalibrationTable 1}

DcmArraySpeedCalibrationEntry  ::= SEQUENCE 
{	
 dcmASCArrNum           DcmArrayNum,
 dcmLogicalIONumber1	DcmLogIONum,
 dcmLogicalIONumber2    DcmLogIONum,
 dcmArraySpeedCalFactor INTEGER,
 dcmASCRowAdmin         DcmRowStatus
}

-- 2.6.16.1 Array Number
dcmASCArrNum OBJECT-TYPE
 SYNTAX   DcmArrayNum
 ACCESS   read-only
 STATUS   mandatory
 DESCRIPTION
 "Indicates the first index into this table.  Refer to DcmArrayNum for a more detailed description."
::= {dcmArraySpeedCalibrationEntry 1}


-- 2.6.16.2 First referenced Logical IO Number 
dcmLogicalIONumber1 OBJECT-TYPE
 SYNTAX   DcmLogIONum
 ACCESS   read-only
 STATUS   mandatory
 DESCRIPTION
 "Indicates the second index into this table expressing the first speed sensor that is being used for array speed calibration purposes.  The Logical IO Number specified must be mapped to the specified array number in the Logical IO to Array Mapping Table.
Refer to DcmLogIONum for a detailed description."
::= {dcmArraySpeedCalibrationEntry 2}

-- 2.6.16.3 Second referenced Logical IO Number 
dcmLogicalIONumber2 OBJECT-TYPE
 SYNTAX   DcmLogIONum
 ACCESS   read-only
 STATUS   mandatory
 DESCRIPTION
 "Indicates the third index into this table expressing the second speed  
sensor that is being used for array speed calibration purposes.  A value of '0' shall indicate that a 2nd speed sensor is not required to determine speed (such as a radar detector or a single loop that can determine speed).  If a 2nd Logical IO Number is required, it must be mapped to the specified array number in the Logical IO to Array Mapping Table.
Refer to DcmLogIONum for a detailed description."
::= {dcmArraySpeedCalibrationEntry 3}

-- 2.6.16.4 Array Speed Calibration Factor
dcmArraySpeedCalFactor  OBJECT-TYPE
 SYNTAX  INTEGER (1..65535)
 ACCESS  read-write
 STATUS  mandatory
 DESCRIPTION
 "Indicates the adjustment factor to calibrate the measured speed results reported by the device  from the 2 speed sensors specified by the two Logical IO Number fields in this row of this table. The algorithm to calculate speed is not defined in this standard.  This is a discrete multiplier with no units with a resolution of .001.    A value of 1000 is equal to 1.000 which would be a multiplier of 1.000 (no change)."
::= {dcmArraySpeedCalibrationEntry 4}

-- 2.6.16.5 Array Speed Calibration Table Row Administration 
dcmASCRowAdmin  OBJECT-TYPE
 SYNTAX   DcmRowStatus
 ACCESS   read-write
 STATUS   optional
 DESCRIPTION
 "This object serves as the table row management item.  The possible 
   values can be found in the definition of the SYNTAX 'DcmRowStatus'."
::= {dcmArraySpeedCalibrationEntry 5}

-- 2.6.17 Max Number of Axles
dcmMaxNumAxles OBJECT-TYPE
 SYNTAX  INTEGER (1..255)
 ACCESS  read-only
 STATUS  optional
 DESCRIPTION
 " indicates the maximum number of axles per vehicle that this device will support. This is a discrete number and has no units."
::= {dcmSiteSetup 17}

-- 2.6.18 Max Number of Filters
dcmMaxFilters OBJECT-TYPE
 SYNTAX  INTEGER (0..255)
 ACCESS  read-only
 STATUS  optional
 DESCRIPTION
 "indicates the maximum number of filters that can be configured in the filter table within this device. "
::= {dcmSiteSetup 18}

-- 2.6.19 Current Number Of Filters 
dcmNumFilters OBJECT-TYPE
 SYNTAX  INTEGER (0..255)
 ACCESS  read-only
 STATUS  optional
 DESCRIPTION
 "indicates the current number of filters configured for this device.  
 This value is updated each time a new filter configuration is added to
 or deleted from the filter table."
::= {dcmSiteSetup 19}

-- A filter defined by the following table always excludes data, e.g. it 
-- filters data out. A filter can be defined with multiple  conditions (see 
-- dcmFilterRowRelation).  Parenthesis are always implied around the first two
-- entries of a filter definition (first two is defined by dcmFilterIndex 
-- values of 1 and 2), then the result of that with the next condition, and so 
-- on.

-- 2.6.20 Maximum Number Of Filter Configuration Table Rows
dcmFCTMaxNumRows OBJECT-TYPE
 SYNTAX DcmMaxNumRows
 ACCESS read-only
 STATUS mandatory
 DESCRIPTION
 "Indicates the maximum number of rows allowed for the Filter Configuration Table."
::= {dcmSiteSetup 20}

-- 2.6.21 Current Number Of Filter Configuration Table Rows
dcmFCTCurNumRows OBJECT-TYPE
 SYNTAX DcmCurNumRows
 ACCESS read-only
 STATUS mandatory
 DESCRIPTION
 "Indicates the current number of rows existing in the Filter Configuration Table."
::= {dcmSiteSetup 21}

-- 2.6.22 Filter Configuration Table 
dcmFilterConfigTable OBJECT-TYPE
 SYNTAX   SEQUENCE OF DcmFilterConfigEntry
 ACCESS   not-accessible
 STATUS   optional
 DESCRIPTION
 "This table is a doubly-indexed table.  It defines the parameters for each filter definition. The table can be managed thru the dcmFilterConfRowAdmin object. Each filter defined by this table includes data (filters data in). Each filter can be defined with multipe conditions (one row per condition). Parenthesis are always implied around the first two criteria of any filter, then the result of that with the next criteria, and so on."
::= {dcmSiteSetup 22}

dcmFilterConfigEntry OBJECT-TYPE
 SYNTAX   DcmFilterConfigEntry 
 ACCESS   not-accessible
 STATUS   mandatory
 DESCRIPTION "..."
 INDEX    {dcmFCFilterNum, dcmFilterIndex}
::= {dcmFilterConfigTable 1}

DcmFilterConfigEntry  ::= SEQUENCE 
{
 dcmFCFilterNum        DcmFilterNum,
 dcmFilterIndex        INTEGER,
 dcmFilterCriteria     OBJECT IDENTIFIER, 
 dcmFilterRelation     INTEGER,
 dcmFilterValue        INTEGER,
 dcmFilterRowRelation  INTEGER,
 dcmFilterConfRowAdmin DcmRowStatus
}

-- 2.6.22.1 Filter Number 
dcmFCFilterNum OBJECT-TYPE
 SYNTAX   DcmFilterNum
 ACCESS   read-only
 STATUS   mandatory
 DESCRIPTION
 "Indicates the first index of a particular filter being defined within 
the device.  Refer to DcmFilterNum for a more detailed description."
::= {dcmFilterConfigEntry 1}

-- 2.6.22.2 Filter Index 
dcmFilterIndex OBJECT-TYPE
 SYNTAX   INTEGER (1..3)
 ACCESS   read-only
 STATUS   mandatory
 DESCRIPTION
 "Indicates the second index of a particular filter.  Each defined filter 
 must have at least one second index defined.  The filters shall be processed in ascending order based on the second index.  The first two entries for any defined filter are processed first, the result of that is then processed with the next row, the result of that with the 4th, etc.."
::= {dcmFilterConfigEntry 2}

-- 2.6.22.3 Filter Criteria
dcmFilterCriteria OBJECT-TYPE
 SYNTAX  OBJECT IDENTIFIER
 ACCESS  read-write
 STATUS  mandatory
 DESCRIPTION
"Indicates which criteria shall be assigned to this filter (e.g. speed, axle class, vehicle length…).  The available criteria are defined in the dcm Vehicle Criteria Node.  Only OID's of objects that are defined as Integers that require 4 or less bytes can be used to configure filters."
::= {dcmFilterConfigEntry 3}

-- 2.6.22.4 Filter Relation 
dcmFilterRelation  OBJECT-TYPE
 SYNTAX   INTEGER 
 {
  greaterThan (1),
  lessThan (2),
  equal (3),
  greaterOrEqual (4),
  lessOrEqual (5),
  notEqual (6),
  logicalAnd (7),
  logicalNot (8)
 }
 ACCESS   read-write
 STATUS   mandatory
 DESCRIPTION "Indicates the relationship between dcmFilterCriteria and dcmFilterValue required to trigger this filter. This data element is valid for this row, not for interrelationship between rows of a particular filter (see dcmFCFilterNum and dcmFilterRowRelation). The values are self-explanatory.
In opposite to the common setup of SNMP MIB objects, this object was purposely setup to NOT include a value of (other).
The values of logicalAnd and logicalNot are used for configuring filters based on bit-by-bit boolean comparisons of the following objects:
dcmVehicleStatusFlag
dcmAxleWeightViolationCode."
::= {dcmFilterConfigEntry 4}

-- 2.6.22.5 Filter Value 
dcmFilterValue  OBJECT-TYPE
 SYNTAX   INTEGER (0.. 4294967295)  --4 bytes
 ACCESS   read-write
 STATUS   mandatory
 DESCRIPTION
"Indicates the value associated with this filter row.  The value shall always be expressed in 4 bytes.  The unit and interpretation of this value shall be dependent on the value of the dcmFilterCriteria object. The dcmFilterCriteria objects are defined in the dcm Vehicle Criteria Node."
::= {dcmFilterConfigEntry 5}

-- 2.6.22.6 Filter Row Relation 
dcmFilterRowRelation  OBJECT-TYPE
 SYNTAX   INTEGER 
 {
  and (1),
  or (2),
  endOfDef (3)
 }
 ACCESS   read-write
 STATUS   mandatory
 DESCRIPTION
 "Indicates how several rows with the same value of the DcmFilterNum object are related to each other. Combines the criteria of a row (dcmFilterIndex) with the next row (next higher value of the dcmFilterIndex object) within the same DcmFilterNum.  It is up to the actual implementation (database population) to ensure that the association of rows is logical. The currently defined values are:
and  – Both criteria of the two rows must be met for the filter to be applied.
or – Either criteria of the two rows must be met for the filter to be applied.
endOfDef  – indicates that the criteria of this row is the last criteria valid for this DcmFilterNum.  
If only one criteria is used per Filter (DcmFilterNum), the value of this object needs to be set to endOfDef (3).
In opposite to the common setup of SNMP MIB objects, this object was purposely setup to NOT include a value of (other)."
::= {dcmFilterConfigEntry 6}

-- 2.6.22.7 Filter Configuration Table Row Administration
dcmFilterConfRowAdmin OBJECT-TYPE
 SYNTAX   DcmRowStatus
 ACCESS   read-write
 STATUS   mandatory
 DESCRIPTION
 "This object serves as the table row management item.  The possible 
values can be found in the definition of the SYNTAX 'DcmRowStatus'."
::= {dcmFilterConfigEntry 7}

-- 2.6.23 Maximum Number Of Logical Output To Filter Table Rows
dcmLOFTMaxNumRows OBJECT-TYPE
 SYNTAX DcmMaxNumRows
 ACCESS read-only
 STATUS mandatory
 DESCRIPTION
 "Indicates the maximum number of rows allowed for the Logical Output To Filter Table."
::= {dcmSiteSetup 23}

-- 2.6.24 Current Number Of Logical Output To Filter Table Rows
dcmLOFTCurNumRows OBJECT-TYPE
 SYNTAX DcmCurNumRows
 ACCESS read-only
 STATUS mandatory
 DESCRIPTION
 "Indicates the current number of rows existing in the Logical Output To Filter Table."
::= {dcmSiteSetup 24}

-- 2.6.25 Logical Output To Filter Mapping Table 
dcmOFMTable OBJECT-TYPE
 SYNTAX   SEQUENCE OF DcmOFMEntry
 ACCESS   not-accessible
 STATUS   optional
 DESCRIPTION
  "This table defines a mapping from a logical output (Logical IO Number which is specifically an output) to one or more filters. Multiple filters can be mapped to a single logical output through multiple rows in this table.  The different filters in each row are related through the Boolean entry in this table.  The Boolean relationships are processed in ascending order (as defined by the 2nd index) of entries assigned to the specified logical output.  The last row associated with each logical output must have the Boolean column set to 'end of definition'.  If an application attempts to set more rows associated with a single logical output than is allowed, an application error of 'exceededMaxNumberOfAllowedOccurrences' shall be set.
This is a double-indexed table.  The table can be managed thru dcmOFMRowAdmin object.  Additionally, this table may be cleared using the User Reset Table."
::= {dcmSiteSetup 25}

dcmOFMEntry OBJECT-TYPE
 SYNTAX   DcmOFMEntry 
 ACCESS   not-accessible
 STATUS   mandatory
 DESCRIPTION "..."
 INDEX {dcmOFMIONum, dcmOFMIndex}
::= {dcmOFMTable 1}

DcmOFMEntry ::= SEQUENCE 
{
 dcmOFMIONum     DcmLogIONum,
 dcmOFMIndex     INTEGER,
 dcmOFMFilterNum DcmFilterNum,
 dcmOFMState     INTEGER,	
 dcmOFMStateTime INTEGER,
 dcmOFMRelation  INTEGER,
 dcmOFMRowAdmin  DcmRowStatus
}

-- 2.6.25.1 OFM IO Num
dcmOFMIONum OBJECT-TYPE
 SYNTAX DcmLogIONum
 ACCESS read-only
 STATUS mandatory
 DESCRIPTION
 "Indicates the first index into this table.  Refer to DcmLogIONum for description."
::= {dcmOFMEntry 1}

-- 2.6.25.2 Output Filter Map Index
dcmOFMIndex OBJECT-TYPE
 SYNTAX   INTEGER (1..255)
 ACCESS   read-only
 STATUS   mandatory
 DESCRIPTION
  "Indicates the second index into this table.  This index must be assigned sequentially.  It is used to map and Boolean relate multiple filters (specified by dcmOFFFilterNum) to a single logical output. The value of dcmOFMRelation column determines the type of Boolean processing to occur on the specified filters. The first two entries are processed first, the result of that is then processed with the next row, the result of that with the 4th, etc."
::= {dcmOFMEntry 2}

-- 2.6.25.3 Filter Number 
dcmOFMFilterNum OBJECT-TYPE
 SYNTAX   DcmFilterNum
 ACCESS   read-write
 STATUS   mandatory
 DESCRIPTION
 "Indicates a defined filter (from the dcm Filter Configuration Table) to be mapped to the output specified by dcmOMFIONum. Refer to DcmFilterNum for a more detailed description."
::= {dcmOFMEntry 3}

-- 2.6.25.4 Output State
dcmOFMState OBJECT-TYPE
 SYNTAX   INTEGER
 {
  other (1),
  turnOn (2),
  turnOff (3),
  pulse (4)
 }
 ACCESS   read-write
 STATUS   mandatory
 DESCRIPTION
 "Indicates the state the output specified by dcmOMFIONum shall go to when the specified defined filter relationship is triggered.  The value of this object shall only be valid in rows in which the value of the dcmOFMRelation object is set to 3 (endOfDef), otherwise the value of this object shall be ignored. The values are:
-other=not defined
-turnOn=specified output shall turn on for the period of time specified by dcmOMFStateTime.  If dcmOMFStateTime=0, the output shall remain in the specified state indefinitely.
-turnOff=specified output shall turn off for the period of time specified by dcmOMFStateTime. If dcmOMFStateTime=0, the output shall remain in the specified state indefinitely.
-pulse=specified output shall pulse one time.  The amount of time the pulse is active for shall be specified by dcmOMFStateTime.  If dcmOMFStateTime=0, the pulse shall be the default pulse time (which is implementation-specific) for the specified output."
::= {dcmOFMEntry 4}

-- 2.6.25.5 Output State Time
dcmOFMStateTime OBJECT-TYPE
 SYNTAX   INTEGER (0..16777215)
 ACCESS   read-write
 STATUS   mandatory
 DESCRIPTION
 "Indicates the time (in milliseconds) that the logical output shall remain in the state specified by dcmOMFState. If dcmOFMState=0, the output shall remain in the specified state indefinitely. 
The value of this object shall only be valid in rows in which the value of the dcmOMFRelation object is set to 3 (endOfDef), otherwise the value of this object shall be ignored."
::= {dcmOFMEntry 5}

-- 2.6.25.6 Output Filter Map Relationship
dcmOFMRelation OBJECT-TYPE
 SYNTAX INTEGER 
 {
  and (1),
  or (2),
  endOfDef (3)
 }
 ACCESS   read-write
 STATUS   mandatory
 DESCRIPTION
 "Indicates how multiple filters can be related together to trigger the specified logical output. It is up to the application to ensure that the rows are populated in the correct sequence to achieve the desired Boolean relationship.  The Boolean relationships are processed in an ascending order as specified by the second index within each logical output.  If 3 rows were defined (1-1-and, 1-2-or, 1-3-end) the result would be that logical output 1 is triggered if ((filter 1 and filter 2) or filter 3)=True.  The currently defined values are:
and (1) – This defines a Boolean 'and' operation between the filter specified in this row and the filter defined in the next row for the same logical output as determined by the second index of this table.  The logical output shall not be triggered unless both filters are true.
or (2) – This defines a Boolean 'or' operation between the filter specified in this row and the filter defined in the next row for the same logical output as determined by the second index of this table.  The logical output shall not be triggered unless either one of the filters are true.
endOfDef (3) – Indicates that this row is the end of the definition for the criteria required to trigger the specified logical output.  
If only one mapping is used per output (this row), the value of this object  shall be set to endOfDef.
In opposite to the common setup of SNMP MIB objects, this object was purposely setup to NOT include a value of (other)."
::= {dcmOFMEntry 6}

-- 2.6.25.7 Output Filter Map Row Admin
dcmOFMRowAdmin OBJECT-TYPE
 SYNTAX   DcmRowStatus 
 ACCESS   read-write
 STATUS   mandatory
 DESCRIPTION
 "Allows management of the associated 'logical output/filter number combination' (this row of this table).  The SYNTAX definition allows to create, delete, disable, or edit the row.  This object cannot be set to 'active' until a row associated with the specified logical output exists with endOfDef.  This is a slightly different usage of this object in that it requires a relationship between multiple rows."
::= {dcmOFMEntry 7}

-- 2.6.26 Max Number of Vehicle ID's
dcmMaxNumVehId OBJECT-TYPE
 SYNTAX  INTEGER (1..255)
 ACCESS  read-only
 STATUS  optional
 DESCRIPTION
 "Indicates the maximum number of vehicle ID's per vehicle that this device shall support. This is a discrete number and has no units."
::= {dcmSiteSetup 26}


-- 2.7 STUDY SETUP NODE
--DCM Study Setup Node
dcmStudyConfig OBJECT IDENTIFIER ::= {dcm 5}
-- This node is an identifier used to group all objects for configuring 
-- one or more studies.  The objects utilized are common to data collection 
-- and monitoring devices.


-- 2.7.1 Current Number Of Studies
dcmNumStudies  OBJECT-TYPE
 SYNTAX INTEGER (0..255)
 ACCESS read-only
 STATUS optional
 DESCRIPTION
 "Indicates the current number of studies defined in the dcmStudyConfigTable within this dcm device."
::= {dcmStudyConfig 1}

-- 2.7.2 Maximum Number of Studies 
dcmMaxNumStudies OBJECT-TYPE
 SYNTAX INTEGER (1..255)
 ACCESS read-only
 STATUS optional
 DESCRIPTION
 "Indicates the maximum number of all types of studies that can be defined within this device.  A typical DCM device will support between 1 and 3 studies being defined simultaneously."
::= {dcmStudyConfig 2}

-- 2.7.3 Maximum Number Of Study Configuration Table Rows
dcmSCTMaxNumRows OBJECT-TYPE
 SYNTAX DcmMaxNumRows
 ACCESS read-only
 STATUS mandatory
 DESCRIPTION
 "Indicates the maximum number of rows allowed for the Study Configuration Table."
::= {dcmStudyConfig 3}

-- 2.7.4 Current Number Of Study Configuration Table Rows
dcmSCTCurNumRows OBJECT-TYPE
 SYNTAX DcmCurNumRows
 ACCESS read-only
 STATUS mandatory
 DESCRIPTION
 "Indicates the current number of rows existing in the Study Configuration Table."
::= {dcmStudyConfig 4}

-- 2.7.5 Study Configuration Table 
dcmStudyConfigTable OBJECT-TYPE
 SYNTAX SEQUENCE OF DcmStudyConfigEntry
 ACCESS not-accessible
 STATUS optional
 DESCRIPTION
 "This table defines the required parameters to configure studies for either data recording or Monitor Modes.  The number of rows in this table cannot exceed the maximum number of studies (dcmMaxNumStudies) and shall be the same as the dcmNumStudies object value. This is a single-indexed table.  The table can be managed thru dcmStudyConfigRowAdmin object."
::= {dcmStudyConfig 5}

dcmStudyConfigEntry OBJECT-TYPE
 SYNTAX DcmStudyConfigEntry 
 ACCESS not-accessible
 STATUS mandatory
 DESCRIPTION "..."
 INDEX {dcmSCStudyNum} 
::= {dcmStudyConfigTable 1}

DcmStudyConfigEntry  ::= SEQUENCE 
{
 dcmSCStudyNum          DcmStudyNum,
 dcmStudyType           INTEGER,
 dcmStartType           INTEGER,
 dcmStartDateTime       Counter,
 dcmEndType             INTEGER,
 dcmEndDateTime         Counter,
 dcmSCFileStudyIndex    DcmFileStudyIndex,
 dcmStudyConfigRowAdmin DcmRowStatus
}

-- 2.7.5.1 Study Number
dcmSCStudyNum OBJECT-TYPE
 SYNTAX DcmStudyNum
 ACCESS read-only
 STATUS mandatory
 DESCRIPTION
 "Indicates the only index into this table. It represents a unique number for each study that is defined within the device in this table.  It is recommended to assign this value sequentially, however deleting studies may produce gaps in the indexes.  It is recommended to use the deleted study number as the next one to assign as an attempt to keep these indexes sequential."
::= {dcmStudyConfigEntry 1}

-- 2.7.5.2 Study Type
dcmStudyType OBJECT-TYPE
 SYNTAX INTEGER 
 {
  other (1),
  binned (2),
  pvr (3),
  event (4),
  arrayParam (5),
  logicalIOParam (6),
  log (7)
 }
 ACCESS read-write
 STATUS mandatory
 DESCRIPTION
 "Indicates the type of study that is being configured within this row. The values are:
- other (1) - Not defined below.
- binned (2) - Processes data based on user-defined aggregated bins (details are configured in Binned Filter Definition Table and Binned Study Configuration Table). 
- pvr (3) - Processes user-defined data for each vehicle (details are configured in PVR Study Configuration Table).
- event (4) - Processes data based on raw IO (details are configured in Event Study Configuration Table and Event To Logical IO Mapping Table).
- arrayParam (5) – Processes sensor array parameter changes to a data file.  The structure of the array parameter data record is defined by the Array Parameter Change Record Table.
- logicalIOParam (6) - Processes logical IO  parameter changes to a data file.  The structure of the logical IO parameter data record is defined by the Logical IO Parameter Change Record Table.
- log (7) – Processes log data to a data file.  The structure of the log records  are defined by the Log Data Record Table."
::= {dcmStudyConfigEntry 2}

-- 2.7.5.3 Study Start Type
dcmStartType OBJECT-TYPE
 SYNTAX   INTEGER 
 {
  other (1),
  now (2),
  nextInterval (3),
  dateTime (4)
 }
 ACCESS   read-write
 STATUS   mandatory
 DESCRIPTION
 "indicates how the study defined in this row is supposed to start.  The values are:
- other = not defined below
- now = as soon as the DCM device receives the command, it shall begin recording.  This may result in having partial data for a recording interval.
- nextInterval = as soon as the next even recording interval starts, the study shall begin recording, e.g., if the  dcmFPRecInt is '3600' (1 hour) recording shall begin at the next full hour.  This will ensure that no partial recording intervals are stored.
- dateTime = The device shall begin recording data at the date/time as specified in the dcmStartDateTime object."
::= {dcmStudyConfigEntry 3}

-- 2.7.5.4 Study Start Date and Time
dcmStartDateTime OBJECT-TYPE
 SYNTAX   Counter
 ACCESS   read-write
 STATUS   mandatory
 DESCRIPTION
 "If Study Start Type is set to dateTime, then this object indicates the date and time at which the study is to start.  The value of this object follows the 'controller-localTime' setup, which specifies the epoch since Midnight January 1, 1970.  For all other selections of Study Start Type, this object is meaningless."
::= {dcmStudyConfigEntry 4}

-- 2.7.5.5 Study End Type
dcmEndType OBJECT-TYPE
 SYNTAX  INTEGER 
 {
  other (1),
  never (2),
  dateTime(3)
 }
 ACCESS   read-write
 STATUS   mandatory
 DESCRIPTION
 "Indicates how long the defined study shall run for.  At the end of the specified time, the study shall be set to idle by the device but it shall not be removed from this table.  The values are:
- other = not defined below
- never = The study shall run forever.  The only way to end the study is to disable it through the Data Recording Enable Table (quitRecording option for Data Recording Control).
- dateTime = the study shall end at the specified date and time specified in the dcmEndDateTime object."
::= {dcmStudyConfigEntry 5}

-- 2.7.5.6 Study End Date and Time
dcmEndDateTime OBJECT-TYPE
 SYNTAX   Counter
 ACCESS   read-write
 STATUS   mandatory
 DESCRIPTION
 "If Study End Type is set to dateTime, then this object indicates the date and time at which the study is to end.  The value of this object follows the 'controller-localTime' setup, which specifies the epoch since Midnight January 1, 1970.  For all other selections of Study End Type, this object is meaningless."
::= {dcmStudyConfigEntry 6}

-- 2.7.5.7 Study File Index
dcmSCFileStudyIndex OBJECT-TYPE
 SYNTAX   DcmFileStudyIndex
 ACCESS   read-write	
 STATUS   mandatory
 DESCRIPTION
 "Defines the file structure number within the File Structure Table (non-zero values).  A value of zero (0) indicates that no data shall be recorded and the study is to be used for Monitor Modes (see the Monitor Enable Table)."
::= {dcmStudyConfigEntry 7}

-- 2.7.5.8 Study Configuration Row Admin
dcmStudyConfigRowAdmin OBJECT-TYPE
 SYNTAX   DcmRowStatus 
 ACCESS   read-write
 STATUS   mandatory
 DESCRIPTION
 "Allows management of the parameters used to configure a study (this row of this table).  The SYNTAX definition allows to create,delete, disable, or edit the row.  If a study is deleted from this table, the device shall delete all rows in any other table that references that study.  It is highly recommended that the application make every attempt to keep the study number sequential (reuse study numbers that have been deleted)."
::= {dcmStudyConfigEntry 8}

-- 2.7.6 Maximum Number Of Array To Study Mapping Table Rows
dcmASMTMaxNumRows OBJECT-TYPE
 SYNTAX DcmMaxNumRows
 ACCESS read-only
 STATUS mandatory
 DESCRIPTION
 "Indicates the maximum number of rows allowed for the Array To Study Mapping Table."
::= {dcmStudyConfig 6}

-- 2.7.7 Current Number Of Array To Study Mapping Table Rows
dcmASMTCurNumRows OBJECT-TYPE
 SYNTAX DcmCurNumRows
 ACCESS read-only
 STATUS mandatory
 DESCRIPTION
 "Indicates the current number of rows existing in the Array To Study Mapping Table."
::= {dcmStudyConfig 7}

-- 2.7.8 Array To Study Mapping Table 
dcmStudyArrayMapTable OBJECT-TYPE
 SYNTAX   SEQUENCE OF DcmStudyArrayMapEntry
 ACCESS   not-accessible
 STATUS   optional
 DESCRIPTION
 "Defines which sensor arrays are mapped to which studies. It is also used to enable/disable sensor arrays assigned to studies.  This is a double-indexed table, with both indices defined in previous tables. The table can be managed thru dcmStudyArrayRowAdmin object.  If a study is deleted from the Study Configuration Table, the device shall delete any entries in this table associated with that study."
::= {dcmStudyConfig 8}

dcmStudyArrayMapEntry OBJECT-TYPE
 SYNTAX   DcmStudyArrayMapEntry 
 ACCESS   not-accessible
 STATUS   mandatory
 DESCRIPTION "..."
 INDEX    {dcmSAMStudyNum, dcmSAMArrNum}
::= {dcmStudyArrayMapTable 1}

DcmStudyArrayMapEntry  ::= SEQUENCE 
{
 dcmSAMStudyNum           DcmStudyNum,
 dcmSAMArrNum             DcmArrayNum,
 dcmStudyArrayEnable      INTEGER,
 dcmStudyArrayRowAdmin    DcmRowStatus
}

-- 2.7.8.1 Study Number
dcmSAMStudyNum OBJECT-TYPE
 SYNTAX DcmStudyNum
 ACCESS read-only
 STATUS mandatory
 DESCRIPTION
 "Indicates the first index into this table. It represents a unique number for each study that is defined within the device in the dcmStudyConfigTable.  Refer to DcmStudyNum for more detail."
::= {dcmStudyArrayMapEntry 1}

-- 2.7.8.2 Array Number
dcmSAMArrNum OBJECT-TYPE
 SYNTAX   DcmArrayNum
 ACCESS   read-only
 STATUS   mandatory
 DESCRIPTION
 "Indicates the first index into this table.  Refer to DcmArrayNum for a more detailed description."
::= {dcmStudyArrayMapEntry 2}

-- 2.7.8.3 Study to Array Enable
dcmStudyArrayEnable OBJECT-TYPE
 SYNTAX   INTEGER 
 {
  enable (1),
  disable (2)
 }
 ACCESS   read-write
 STATUS   mandatory
 DESCRIPTION
 "Indicates whether a particular defined array is active within the specified study.

enable – sensor inputs associated with this array shall be processed by the device.
disable – sensor inputs associated with this array shall not be processed by the device.  The device may choose to either ignore those sensor inputs, or turn off the sensors within the Physical to Logical IO Mapping Table.  Typically an array may be turned off for diagnostic purposes.
In opposite to the common setup of SNMP MIB objects, this object was purposely setup to NOT include a value of (other).  "
::= {dcmStudyArrayMapEntry 3}

-- 2.7.8.4 Array to Study Mapping Table Row Admin
dcmStudyArrayRowAdmin OBJECT-TYPE
 SYNTAX   DcmRowStatus 
 ACCESS   read-write
 STATUS   mandatory
 DESCRIPTION
 "Allows management of the parameters used to configure a study (this row of this table).  The SYNTAX definition allows to create,delete, disable, or edit the row. "
::= {dcmStudyArrayMapEntry 4}

-- 2.7.9 Maximum Number Of Filter To Study Mapping Table Rows
dcmFSMTMaxNumRows OBJECT-TYPE
 SYNTAX DcmMaxNumRows
 ACCESS read-only
 STATUS mandatory
 DESCRIPTION
 "Indicates the maximum number of rows allowed for the Filter To Study Mapping  Table."
::= {dcmStudyConfig 9}

-- 2.7.10 Current Number Of Filter To Study Mapping Table Rows
dcmFSMTCurNumRows OBJECT-TYPE
 SYNTAX DcmCurNumRows
 ACCESS read-only
 STATUS mandatory
 DESCRIPTION
 "Indicates the current number of rows existing in the Filter To Study Mapping Table."
::= {dcmStudyConfig 10}

-- 2.7.11 Filter to Study Mapping Table 
dcmStudyFilterMapTable OBJECT-TYPE
 SYNTAX   SEQUENCE OF DcmStudyFilterMapEntry
 ACCESS   not-accessible
 STATUS   optional
 DESCRIPTION
 "Defines the parameters to map selected filters to each of the defined studies.  
This is a double-indexed table, with both indices defined in previous tables. The table can be managed thru dcmStudyFilterMapRowAdmin object.
Multiple filters may be assigned to the same study.  The first two filters assigned to a study shall be processed, the result of that processed with the next filter assigned to the study, and so on."
::= {dcmStudyConfig 11}

dcmStudyFilterMapEntry OBJECT-TYPE
 SYNTAX   DcmStudyFilterMapEntry 
 ACCESS   not-accessible
 STATUS   mandatory
 DESCRIPTION "..."
 INDEX    {dcmSFMStudyNum, dcmSFMFilterNum}
::= {dcmStudyFilterMapTable 1}

DcmStudyFilterMapEntry  ::= SEQUENCE 
{	
 dcmSFMStudyNum            DcmStudyNum,
 dcmSFMFilterNum           DcmFilterNum,
 dcmStudyFilterRelation	   INTEGER,
 dcmStudyFilterMapRowAdmin DcmRowStatus
}

-- 2.7.11.1 Study Number
dcmSFMStudyNum OBJECT-TYPE
 SYNTAX DcmStudyNum
 ACCESS read-only
 STATUS mandatory
 DESCRIPTION
 "Indicates the first index into this table. It represents a unique number for each study that is defined within the device in the dcmStudyConfigTable.  Refer to DcmStudyNum for more detail."
::= {dcmStudyFilterMapEntry 1}

-- 2.7.11.2 Filter Number
dcmSFMFilterNum OBJECT-TYPE
 SYNTAX   DcmFilterNum
 ACCESS   read-only
 STATUS   mandatory
 DESCRIPTION
 "Indicates a defined filter (from the dcm Filter Configuration Table) to be mapped to the study specified by dcmSFMStudyNum. Refer to DcmFilterNum for a more detailed description."
::= {dcmStudyFilterMapEntry 2}

-- 2.7.11.3 Study to Filter Mapping Relationship
dcmStudyFilterRelation OBJECT-TYPE
 SYNTAX INTEGER 
 {
  and (1),
  or (2),
  endOfDef (3)
 }
 ACCESS   read-write
 STATUS   mandatory
 DESCRIPTION
 "Indicates how several rows (filters) with the same value of the dcmSFMStudyNum object are related to each other. It is up to the actual implementation (database population) to ensure that the association of rows is logical.  The first two entries for any defined filter are processed first, the result of that is then processed with the next row, the result of that with the 4th, etc. The currently defined values are:
and (1) – combine the criteria of this row (dcmSFMFilterNum) with the next row (next higher value of the dcmSFMFilterNum object) within the same dcmSFMStudyNum.
or (2) – select the criteria of either this row (dcmSFMFilterNum) or of the next row (next higher value of the dcmSFMFilterNum object) within the same dcmSFMStudyNum.
endOfDef (3) – indicates that the criteria of this row is the last criteria valid for this dcmSFMStudyNum.  
If only one criteria is used per study (dcmSFMStudyNum), the value of this object shall  be set to 'endOfDef'.
In opposite to the common setup of SNMP MIB objects, this object was purposely setup to NOT include a value of (other)."
::= {dcmStudyFilterMapEntry 3}

-- 2.7.11.4 Filter to Study Mapping Table Row Admin
dcmStudyFilterMapRowAdmin OBJECT-TYPE
 SYNTAX   DcmRowStatus 
 ACCESS   read-write
 STATUS   mandatory
 DESCRIPTION
 "Allows management of the parameters used to configure a study filter (this row of this table).  The SYNTAX definition allows to create, delete, disable, or edit the row. If any of the filters are deleted, the device shall automatically delete them from this table.  A value of 'createAndGo' is only valid in rows in which the Study to Filter Mapping Relationship is set to EndOfDef."
::= {dcmStudyFilterMapEntry 4}
-- 2.8 STUDY DATA SETUP NODE
--DCM Study Data Setup Node
dcmStudyDataSetup OBJECT IDENTIFIER ::= {dcm 6}
-- This node is an identifier used to group all objects for configuring 
-- a data collection session that are common to data collection and 
-- monitoring devices.

-- 2.8.1 Display Length Units
dcmLengthUnits OBJECT-TYPE
 SYNTAX INTEGER 
 {
  centimeter (1), -- internal units
  decimeter  (2),
  meter      (3),
  inches     (4),
  tenthFeet  (5),
  feet       (6)
 }
 ACCESS read-write
 STATUS optional
 DESCRIPTION
 "Indicates the units in which length is displayed for ASCII Monitor Mode output and/or any local user interface (keyboard/display) that is used to enter length such as bin limits or length filter limits. The length values shall always be stored in internal units as defined for each object and not in display units.
The currently defined values are:
 -centimeter (1) – 0.01 meter (internal units), (1 centimeter=0.3937 inches)
 -decimeter (2) – 0.1 meter (1 decimeter=3.937 inches)
 -meter (3) – (1 meter=39.37 inches=3.281 feet)
 -inches (4) – (1 inch=2.54 centimeters)
 -tenthFeet (5) – 0.1 feet (1 foot=12 inches)
 -feet (6) – (1 foot=12 inches)
"
::= {dcmStudyDataSetup 1}

-- 2.8.2 Display Speed Units
dcmSpeedUnits OBJECT-TYPE
 SYNTAX INTEGER 
 {
  cms (1), -- internal units
  kmh (2),
  mph (3)
 }
 ACCESS read-write
 STATUS optional
 DESCRIPTION
 "Indicates the units in which speed is displayed for ASCII Monitor Mode output and/or any local user interface (keyboard/display) that is used to enter speed such as bin limits or speed filter limits. The speed values shall always be stored in internal units as defined for each object and not in display units.
The currently defined values are:
 -cms (1) – centimeters per second (internal units)
 -kmh (2) – kilometers per hour
 -mph (3) – miles per hour
"
::= {dcmStudyDataSetup 2}

-- 2.8.3 Display Weight Units
dcmWeightUnits OBJECT-TYPE
 SYNTAX INTEGER 
 {
  tenthTonne (1),
  tenthKips  (2),
  pounds     (3),
  kilograms  (4), -- internal units
  kips       (5)
 }
 ACCESS read-write
 STATUS optional
 DESCRIPTION
 "Indicates the units in which weight is displayed for ASCII Monitor Mode output and/or any local user interface (keyboard/display) that is used to enter weight such as bin limits or weight filter limits. The weight values shall always be stored in internal units as defined for each object and not in display units.
The currently defined values are:
 -tenthTonne (1) – 0.1 Tonne (1 Tonne=2204.62 pounds)
 -tenthKips (2) – 0.1 Kips (1 KIP=1000 pounds)
 -pounds (3) – (1 pound=0.4536 kilograms)
 -kilograms (4) – internal units, (1 kilogram=2.2046 pounds)
 -kips (5) – 1 kip (1 KIP=1000 pounds)
"
::= {dcmStudyDataSetup 3}

-- 2.8.4 Maximum Number of Headings For All Studies
dcmMaxNumHeadings  OBJECT-TYPE
 SYNTAX INTEGER (0..255)
 ACCESS read-only
 STATUS optional
 DESCRIPTION
 "Indicates the maximum number of headings (which are used in the Binned Study Configuration Table to configure studies) that can be configured for all binned studies. A typical DCM device will support between 1 to 3 headings that can be defined for each study giving a typical maximum of between 3 to 9 headings for all studies.  As an example, if the max is 9 headings, there could be 6 headings assigned to study 1, 1 heading to study 2 and 2 headings to study 3."
::= {dcmStudyDataSetup 4}

-- 2.8.5 Maximum Number of Bins For All Studies
dcmMaxNumBins OBJECT-TYPE
 SYNTAX INTEGER (0..65535)
 ACCESS read-only
 STATUS optional
 DESCRIPTION
 "Indicates the maximum number of bins that can be defined over all binned studies.  A typical DCM device may support a maximum binning of 15 classes by 15 speeds by 4 lanes (15x15x4)=900 bins for all studies.  As an example, the 900 bins could also be broken into 200 bins for study 1, 500 bins for study 2 and 200 bins for study 3.  The 200 bins for study 1 could then be broken up into 20 bins for heading 1 of study 1 and 10 bins for heading 2 of study 1 (20 bins x 10 bins=200 bins)."
::= {dcmStudyDataSetup 5}

-- 2.8.6 Maximum Number Of Binned Filter Definition Table Rows
dcmBFDTMaxNumRows OBJECT-TYPE
 SYNTAX DcmMaxNumRows
 ACCESS read-only
 STATUS mandatory
 DESCRIPTION
 "Indicates the maximum number of rows allowed for the Binned Filter Definition Table."
::= {dcmStudyDataSetup 6}

-- 2.8.7 Current Number Of Binned Filter Definition Table Rows
dcmBFDTCurNumRows OBJECT-TYPE
 SYNTAX DcmCurNumRows
 ACCESS read-only
 STATUS mandatory
 DESCRIPTION
 "Indicates the current number of rows existing in the Binned Filter Definition Table."
::= {dcmStudyDataSetup 7}

-- 2.8.8 Binned Filter Definition Table 
dcmBinnedFilterDefTable OBJECT-TYPE
 SYNTAX   SEQUENCE OF DcmBinnedFilterDefEntry
 ACCESS   not-accessible
 STATUS   optional
 DESCRIPTION
 "This table is used to create definitions of ranges that can be applied to bins in the Bin Relation Table. This is a double-indexed table. The table can be managed thru dcmBinnedFilterDefRowAdmin object.  It is recommended that all indexes be assigned sequentially by the application.  There can be multiple ranges assigned to any one Binned Filter.  Parenthesis are always implied around the first two entries assigned to the same Binned Filter for processing.  The results of that are then processed with the next range assigned to this binned filter.  Configuring a binned study with two headings (15 bins of classification x 12 bins of speed) would require defining 27 bins (entries in this table), 15 bins of class + the 12 bins of speed.
--Note that the value stored in each bin is an aggregate count and not a 
--calculated value (e.g. a bin cannot contain the average gross weight of
--vehicles, but it can contain how many vehicles had an average gross
--weight that is within the bin range limits)."
::= {dcmStudyDataSetup 8}

dcmBinnedFilterDefEntry OBJECT-TYPE
 SYNTAX   DcmBinnedFilterDefEntry 
 ACCESS   not-accessible
 STATUS   mandatory
 DESCRIPTION "..."
 INDEX   {dcmBFDBinnedFilterNum, dcmBinnedFilterIndex}
::= {dcmBinnedFilterDefTable 1}

DcmBinnedFilterDefEntry  ::= SEQUENCE 
{
 dcmBFDBinnedFilterNum      DcmBinnedFilterNum,
 dcmBinnedFilterIndex       INTEGER,
 dcmBinHeading              OBJECT IDENTIFIER, -- (reference objects created 
                             -- for each of the enumerations from 
                             -- the Vehicle Criteria Table.)
 dcmBinMinimumValue         INTEGER,
 dcmBinMaximumValue         INTEGER,
 dcmBinNumberIndexRelation  INTEGER,
 dcmBinnedFilterDefRowAdmin DcmRowStatus
}

-- 2.8.8.1 Binned Filter Number
dcmBFDBinnedFilterNum OBJECT-TYPE
 SYNTAX   DcmBinnedFilterNum
 ACCESS   read-only	
 STATUS   mandatory
 DESCRIPTION
 "Indicates the first index into this table.  It represents a unique number for each binned filter that is being defined within the device.  It is strongly suggested that the numbering is assigned sequentially.  This number can never exceed the maximum number of bins for all studies object (dcmMaxNumBins). Refer to DcmBinnedFilterNum for more information."
::= {dcmBinnedFilterDefEntry 1}

-- 2.8.8.2 Binned Filter Index
dcmBinnedFilterIndex OBJECT-TYPE
 SYNTAX   INTEGER (1..255)
 ACCESS   read-only	
 STATUS   mandatory
 DESCRIPTION
 "Indicates the second index into this table.  This value allows assigning more than one heading type (and the associated lower and upper limit) to a binned filter (e.g. assign class 9 or class 11 to this bin). It is strongly suggested that the numbering is assigned sequentially."
::= {dcmBinnedFilterDefEntry 2}

-- 2.8.8.3 Bin Heading
dcmBinHeading OBJECT-TYPE
 SYNTAX   OBJECT IDENTIFIER
 ACCESS   read-write
 STATUS   mandatory
 DESCRIPTION
 "This contains the OID of the type of data (taken from the dcm vehicle criteria node) to be binned for this Binned Filter definition. A volume study can be configured by specifying the Array Number OID."
::= {dcmBinnedFilterDefEntry 3}

-- 2.8.8.4 Bin Minimum Value
dcmBinMinimumValue OBJECT-TYPE
 SYNTAX   INTEGER (0..16777215)
 ACCESS   read-write
 STATUS   mandatory
 DESCRIPTION
 "Indicates the lower range value for this bin (this row of the table). The meaning of this value is dependent on the value of the dcmBinHeading object assigned to this row. When binning data, all compare values that are greater than or equal to the value of this object and less than the value of dcmBinMaximumValue for this Binned Filter must be assigned to this bin."
::= {dcmBinnedFilterDefEntry 4}

-- 2.8.8.5 Bin Maximum Value
dcmBinMaximumValue OBJECT-TYPE
 SYNTAX   INTEGER (0..16777215)
 ACCESS   read-write
 STATUS   mandatory
 DESCRIPTION
 "Indicates the upper range value for this bin (this row of the table). The meaning of this value is dependent on the value of the dcmBinHeading object assigned to this row.  All compare values that are smaller than the value of this object and greater than or equal to the dcmBinMinimumValue for this Binned Filter must be assigned to this bin."
::= {dcmBinnedFilterDefEntry 5}

-- 2.8.8.6 Bin Number to Index Relationship
dcmBinNumberIndexRelation OBJECT-TYPE
 SYNTAX   INTEGER 
 {
  and (1), 
  or (2), 
  endOfDef (3) 
 }
 ACCESS   read-write
 STATUS   mandatory
 DESCRIPTION
 "Indicates how several rows with the same value of the dcmBinnedFilterNumber object are related to each other. It is up to the actual implementation (database population) to ensure that the association of rows is logical. The first two entries for any defined binned filters are processed first, the result of that is then processed with the next row, the result of that with the 4th, etc.  The currently defined values are:
and (1) – combine the criteria of this row with the next row (next higher value of the secondary index object) within the same primary index number object.
or (2) – select the criteria of either this row or that of the next row (next higher value of the same secondary index object) within the same primary index number object.
endOfDef (3) – indicates that the criteria of this row is the last criteria valid for this primary index number object.  
If only one dcmFilterCriteria is used per binned filter, the value of this object shall be set to 'endOfDef'.
In opposite to the common setup of SNMP MIB objects, this object was purposely setup to NOT include a value of (other)."
::= {dcmBinnedFilterDefEntry 6}

-- 2.8.8.7 Binned Filter Definition Table Row Admin
dcmBinnedFilterDefRowAdmin OBJECT-TYPE
 SYNTAX   DcmRowStatus 
 ACCESS   read-write
 STATUS   mandatory
 DESCRIPTION
 "Allows management of the parameters used to configure the definitions of a binned filter (this row of this table).  The SYNTAX definition allows to create, delete, disable, or edit the row."
::= {dcmBinnedFilterDefEntry 7}
	
-- 2.8.9 Maximum Number Of Binned Study Configuration Table Rows
dcmBSCTMaxNumRows OBJECT-TYPE
 SYNTAX DcmMaxNumRows
 ACCESS read-only
 STATUS mandatory
 DESCRIPTION
 "Indicates the maximum number of rows allowed for the Binned Study Configuration Table."
::= {dcmStudyDataSetup 9}

-- 2.8.10 Current Number Of Binned Study Configuration Table Rows
dcmBSCTCurNumRows OBJECT-TYPE
 SYNTAX DcmCurNumRows
 ACCESS read-only
 STATUS mandatory
 DESCRIPTION
 "Indicates the current number of rows existing in the Binned Study Definition Table."
::= {dcmStudyDataSetup 10}

-- 2.8.11 Binned Study Configuration Table 
dcmBinSCTable OBJECT-TYPE
 SYNTAX   SEQUENCE OF DcmBinSCEntry
 ACCESS   not-accessible
 STATUS   optional
 DESCRIPTION
 "This table is used to relate Binned Filters to headings within studies (e.g. Study 1 Heading 1 Bin 1 is Speed (0-10mph),…). This is a triple-indexed table. The table can be managed thru dcmBSCRowAdmin object.  If a Binned Filter is deleted in the Binned Filter Definition Table, the device shall automatically delete any entry within this table that refers to the deleted Binned Filter Number."
::= {dcmStudyDataSetup 11}

dcmBinSCEntry OBJECT-TYPE	
 SYNTAX   DcmBinSCEntry 
 ACCESS   not-accessible
 STATUS   mandatory
 DESCRIPTION "..."
 INDEX    {dcmBSCStudyNum, dcmBSCHeadingNum, dcmBSCLabelNum}
::= {dcmBinSCTable 1}

DcmBinSCEntry  ::= SEQUENCE 
{
 dcmBSCStudyNum   DcmStudyNum,
 dcmBSCHeadingNum INTEGER,
 dcmBSCLabelNum   INTEGER,
 dcmBSCFilterNum  DcmBinnedFilterNum,
 dcmBSCRowAdmin   DcmRowStatus
}

-- 2.8.11.1 Study Number
dcmBSCStudyNum OBJECT-TYPE
 SYNTAX DcmStudyNum
 ACCESS read-only
 STATUS mandatory
 DESCRIPTION
 "Indicates the first index into this table. It represents a unique number for each study that is defined within the device in the dcmStudyConfigTable.  Refer to DcmStudyNum for more detail."
::= {dcmBinSCEntry 1}

-- 2.8.11.2 Heading Number
dcmBSCHeadingNum OBJECT-TYPE
 SYNTAX   INTEGER (1..255)
 ACCESS   read-only
 STATUS   mandatory
 DESCRIPTION
 "Indicates the second index into this table.  It represents a unique heading number for each study that is being defined within the device.  It is strongly suggested that the numbering is assigned sequentially.  Typically a device would support up to 3 headings per study.  A Boolean 'and' is always implied across all of the specified headings for a study (e.g. if 3 bins of class (1,2,3) are specified for heading 1 of study 1 and 2 bins of speed (0-5mph, 5-10mph) are specified for heading 2 of study 1, then bin 1 would be any vehicle that was a class 1 and had a speed between 0-5mph, bin 2 would be any vehicle that was a class 2 and had a speed between 0-5mph, …).  The combination of all the headings specified for all the studies shall never exceed the maximum number of headings for all studies object (dcmMaxNumHeadings)."
::= {dcmBinSCEntry 2}

-- 2.8.11.3 Bin Label Number
dcmBSCLabelNum OBJECT-TYPE
 SYNTAX   INTEGER (1..255)
 ACCESS   read-only
 STATUS   mandatory
 DESCRIPTION
 "Indicates the third index into this table.  This value allows assigning more than one bin label to each heading number and each study number. For example, if study 1 heading 1 required 5 bins to be assigned, 5 rows would be required with this index spanning from 1 to 5. It is strongly suggested that the numbering is assigned sequentially."
::= {dcmBinSCEntry 3}

-- 2.8.11.4 Binned Filter Number
dcmBSCFilterNum OBJECT-TYPE
 SYNTAX   DcmBinnedFilterNum
 ACCESS   read-only	
 STATUS   mandatory
 DESCRIPTION
 "This object represents a unique number for each binned filter that has been defined within the 'dcm Binned Filter Definition Table'.  Refer to DcmBinnedFilterNum for more information."
::= {dcmBinSCEntry 4}	

-- 2.8.11.5 Bin Relation Table Row Admin
dcmBSCRowAdmin OBJECT-TYPE
 SYNTAX   DcmRowStatus 
 ACCESS   read-write
 STATUS   mandatory
 DESCRIPTION
 "Allows management of the parameters used to configure the relations of a binned filter (this row of this table).  The SYNTAX definition allows to create, delete, disable, or edit the row."
::= {dcmBinSCEntry 5}

-- 2.8.12 Maximum Number Of PVR Study Configuration Table Rows
dcmPSCTMaxNumRows OBJECT-TYPE
 SYNTAX DcmMaxNumRows
 ACCESS read-only
 STATUS mandatory
 DESCRIPTION
 "Indicates the maximum number of rows allowed for the PVR Study Configuration Table."
::= {dcmStudyDataSetup 12}

-- 2.8.13 Current Number Of PVR Study Configuration Table Rows
dcmPSCTCurNumRows OBJECT-TYPE
 SYNTAX DcmCurNumRows
 ACCESS read-only
 STATUS mandatory
 DESCRIPTION
 "Indicates the current number of rows existing in the PVR Study Configuration Table."
::= {dcmStudyDataSetup 13}

-- 2.8.14 PVR Study Configuration Table 
dcmPvrStudyConfigTable OBJECT-TYPE
 SYNTAX   SEQUENCE OF DcmPvrStudyConfigEntry
 ACCESS   not-accessible
 STATUS   optional
 DESCRIPTION
 "This is a doubly-indexed table.  It defines the parameters to configure PVR studies. The parameters specified define both the pvr study as well as the structure for the data packets to be stored in the Data Structure Table. The table can be managed thru dcmPvrStudyConfigRowAdmin object.  If a study is deleted from the Study Configuration Table, any entries within this table that refer to that study shall be automatically deleted by the device."
::= {dcmStudyDataSetup 14}

dcmPvrStudyConfigEntry OBJECT-TYPE
 SYNTAX   DcmPvrStudyConfigEntry 
 ACCESS   not-accessible
 STATUS   mandatory
 DESCRIPTION "..."
 INDEX {dcmPSCStudyNum, dcmPvrStudyIndex}
::= {dcmPvrStudyConfigTable 1}

DcmPvrStudyConfigEntry  ::= SEQUENCE 
{
 dcmPSCStudyNum            DcmStudyNum,
 dcmPvrStudyIndex          INTEGER, 
 dcmPvrParam               OBJECT IDENTIFIER, 
 dcmPvrStudyConfigRowAdmin DcmRowStatus
}

-- 2.8.14.1 Study Number
dcmPSCStudyNum OBJECT-TYPE
 SYNTAX DcmStudyNum
 ACCESS read-only
 STATUS mandatory
 DESCRIPTION
 "Indicates the first index into this table. It represents a unique number for each study that is defined within the device in the dcmStudyConfigTable.  Refer to DcmStudyConfig for more detail."
::= {dcmPvrStudyConfigEntry 1}

-- 2.8.14.2 PVR Study Index
dcmPvrStudyIndex OBJECT-TYPE
 SYNTAX INTEGER (1..255)
 ACCESS read-only
 STATUS mandatory
 DESCRIPTION
 "indicates the second index into this table.  This allows specifying to store multiple vehicle parameters for each study."
::= {dcmPvrStudyConfigEntry 2}

-- 2.8.14.3 PVR Parameter
dcmPvrParam OBJECT-TYPE
 SYNTAX   OBJECT IDENTIFIER
 ACCESS   read-write
 STATUS   mandatory
 DESCRIPTION
 "This field contains the OID of the specified pvr parameter to store from the dcm Vehicle Criteria node.  The OID specified must be a full OID from the root of the iso tree, relative OID's cannot be used.  This allows referring to objects outside of this MIB. The objects specified here can be either single or multi-occurrence objects as defined by the object referred to by this OID in the Vehicle Criteria Node.  Refer to the description at the beginning of the Vehicle Criteria Node. The order of the PVR parameters, in this table, specifies the order of the data in the PVR data packet."
::= {dcmPvrStudyConfigEntry 3}

-- 2.8.14.4 PVR Study Configuration Table Row Admin
dcmPvrStudyConfigRowAdmin OBJECT-TYPE
 SYNTAX   DcmRowStatus 
 ACCESS   read-write
 STATUS   mandatory
 DESCRIPTION
 "Allows management of the parameters used to configure a PVR study (this row of this table).  The SYNTAX definition allows to create, delete, disable, or edit the row."
::= {dcmPvrStudyConfigEntry 4}

-- 2.8.15 Maximum Number Of Event Study Configuration Table Rows
dcmESCTMaxNumRows OBJECT-TYPE
 SYNTAX DcmMaxNumRows
 ACCESS read-only
 STATUS mandatory
 DESCRIPTION
 "Indicates the maximum number of rows allowed for the Event Study Configuration Table."
::= {dcmStudyDataSetup 15}

-- 2.8.16 Current Number Of Event Study Configuration Table Rows
dcmESCTCurNumRows OBJECT-TYPE
 SYNTAX DcmCurNumRows
 ACCESS read-only
 STATUS mandatory
 DESCRIPTION
 "Indicates the current number of rows existing in the Event Study Configuration Table."
::= {dcmStudyDataSetup 16}

-- 2.8.17 Event Study Configuration Table 
dcmEventStudyConfigTable OBJECT-TYPE
 SYNTAX   SEQUENCE OF DcmEventStudyConfigEntry
 ACCESS   not-accessible
 STATUS   optional
 DESCRIPTION
 "This table is used to configure an Event Study.  The fields configured in this table define the number of bits to identify the size of an event and how frequently a timer event would be placed in the data. This uses Study Number as the single-index into the table.  This table requires row administration.  There shall be one row defined in this table for each required event study. The table can be managed thru dcmEventStudyConfigRowAdmin object."
::= {dcmStudyDataSetup 17}

dcmEventStudyConfigEntry OBJECT-TYPE
 SYNTAX   DcmEventStudyConfigEntry 
 ACCESS   not-accessible
 STATUS   mandatory
 DESCRIPTION "..."
 INDEX    {dcmESCStudyNum}
::= {dcmEventStudyConfigTable 1}

DcmEventStudyConfigEntry  ::= SEQUENCE 
{
 dcmESCStudyNum              DcmStudyNum,
 dcmEventNumberSize          INTEGER,
 dcmTimerEventMaxPeriod      INTEGER,
 dcmEventStudyConfigRowAdmin DcmRowStatus
 }
-- 2.8.17.1 Study Number
dcmESCStudyNum OBJECT-TYPE
 SYNTAX DcmStudyNum
 ACCESS read-only
 STATUS mandatory
 DESCRIPTION
 "Indicates the only index into this table. It represents a unique number for each study that is defined within the device in the dcmStudyConfigTable.  Refer to DcmStudyConfig for more detail."
::= {dcmEventStudyConfigEntry 1}

-- 2.8.17.2 Event Number Size
dcmEventNumberSize OBJECT-TYPE
 SYNTAX   INTEGER (1..255)
 ACCESS   read-write
 STATUS   mandatory
 DESCRIPTION
 "This indicates the number of bits required to store  an event number.  This shall reflect the total number of events that are mapped to this event study in the Event To Logical IO Mapping Table.  For example, if this value is set to two, then there can only be a maximum of four distinct events that can be identified. 
The value cannot be set to zero (0), since it would indicate that there are no event #'s to refer to in the Event To Logical IO Mapping Table."
::= {dcmEventStudyConfigEntry 2}

-- 2.8.17.3 Timer Event Maximum Period
dcmTimerEventMaxPeriod OBJECT-TYPE
 SYNTAX   INTEGER (1..4294967295)
 ACCESS   read-write
 STATUS   mandatory
 DESCRIPTION
 "This field identifies the maximum number of milliseconds that can be contained in the timestamp stored within each event(see dcmTimeStampSize).   If a timer is defined as an event # in the Event To Logical IO Mapping table, the value of dcmTimerEventMaxPeriod defines the period between timer events.  If a timer is not identified as an event in the Event To Logical IO Mapping Table, no timer events shall be stored, this field shall be ignored."
::= {dcmEventStudyConfigEntry 3}

-- 2.8.17.4 Event Study Config Table Row Admin
dcmEventStudyConfigRowAdmin OBJECT-TYPE
 SYNTAX   DcmRowStatus 
 ACCESS   read-write
 STATUS   mandatory
 DESCRIPTION
 "Allows management of the parameters used to configure an event study (this row of this table).  The SYNTAX definition allows to create, delete, disable, or edit the row."
::= {dcmEventStudyConfigEntry 4}

-- 2.8.18 Maximum Number Of Event To Logical IO Mapping Table Rows
dcmELIMTMaxNumRows OBJECT-TYPE
 SYNTAX DcmMaxNumRows
 ACCESS read-only
 STATUS mandatory
 DESCRIPTION
 "Indicates the maximum number of rows allowed for the Event To Logical IO Mapping Table."
::= {dcmStudyDataSetup 18}

-- 2.8.19 Current Number Of Event To Logical IO Mapping Table Rows
dcmELIMTCurNumRows OBJECT-TYPE
 SYNTAX DcmCurNumRows
 ACCESS read-only
 STATUS mandatory
 DESCRIPTION
 "Indicates the current number of rows existing in the Event To Logical IO Mapping Table."
::= {dcmStudyDataSetup 19}

-- 2.8.20 Event To Logical IO Mapping Table 
dcmEventConfigTable OBJECT-TYPE
 SYNTAX   SEQUENCE OF DcmEventConfigEntry
 ACCESS   not-accessible
 STATUS   optional
 DESCRIPTION
 "This table maps logical IO's to a unique event number within a particular study.  The parameters allow defining the structure of each event data that is to be recorded.  An event is defined as a specific state of a logical IO and given a unique event # for a particular study.  The parameters are  related to a particular study number to allow for multiple structures for the same input.
An IO event record as stored in the data portion of an event data packet would consist of an Event # (dcmEventNum), Event Value (# of bits specified by dcmEventValueSize), Timestamp (# of bits specified by dcmTimestampSize).  The size of the IO event would be the sum of the Event # Size (dcmEventNumberSize), Event Value Size (dcmEventValueSize) and the Timestampsize (dcmTimestampSize).
Therefore to decipher the bitstream in an event record, the  first x bits (dcmEventNumberSize) of each data element would identify the Event Number and this table would define how many bits follow for the event value and event timestamp.
This is a single-indexed table. The index is assigned sequentially and the table requires row administration.  There shall be one row in this table for each event # mapped to an event study.
The table can be managed thru the dcmEventConfigRowAdmin object."
::= {dcmStudyDataSetup 20}

dcmEventConfigEntry OBJECT-TYPE
 SYNTAX   DcmEventConfigEntry 
 ACCESS   not-accessible
 STATUS   mandatory
 DESCRIPTION "..."
 INDEX    {dcmECStudyNum,dcmEventConfigNumber}
::= {dcmEventConfigTable 1}

DcmEventConfigEntry ::= SEQUENCE 
{
 dcmECStudyNum          DcmStudyNum,
 dcmEventConfigNumber   INTEGER,
 dcmEventNumber         INTEGER,
 dcmECIONum             DcmLogIONum,
 dcmLogicalIOState      INTEGER,
 dcmEventValueSize      INTEGER,
 dcmTimestampSize       INTEGER,
 dcmEventConfigRowAdmin DcmRowStatus
}
-- 2.8.20.1 
-- 2.8.20.2 Study Number
dcmECStudyNum OBJECT-TYPE
 SYNTAX DcmStudyNum
 ACCESS read-write
 STATUS mandatory
 DESCRIPTION
 "Indicates a unique number for each study that is defined within the device in the dcmStudyConfigTable.  Refer to DcmStudyConfig for more detail."
::= {dcmEventConfigEntry 1}

-- 2.8.20.3 Event Configuration Number
dcmEventConfigNumber OBJECT-TYPE
 SYNTAX   INTEGER (1..255)
 ACCESS   read-only
 STATUS   mandatory
 DESCRIPTION
 "This is a unique number that is used to create a sequential index (within each Study number) for this table.  This is the second index of the table. Although dcmEventNumber could be used as the second index, it would require a larger number of bits to store an event since an index cannot be assigned a value of zero and thus would have to start at one.  For example, a study with two events (Event # 1, Event # 2, (note that Event # 0 cannot be used)) would have to use two bits in each event record rather than one (two bits are required to represent the number 2 for Event # 2).  Using Event Config # as a separate index provides for the least number of bits to be stored in the event data record."
::= {dcmEventConfigEntry 2}

-- 2.8.20.4 Event Number
dcmEventNumber OBJECT-TYPE
 SYNTAX   INTEGER (0..255)
 ACCESS   read-only
 STATUS   mandatory
 DESCRIPTION
 "This is a unique sequential number assigned by the equipment for each event within this study.  The first event number shall be 0 and subsequent events shall be numbered sequentially for the same study number in order to limit the number of bits necessary to identify all the events for a study.  Note that the event number can be repeated for different studies, e.g. there can be an event number 0 for Study 1 and event number 0 for Study 2. When a study is validated or set to prime, the device shall verify that all event numbers relative to the same study in this table are sequential.  An application error of 'validationFailed' shall be reported if they are not."
::= {dcmEventConfigEntry 3}

-- 2.8.20.5 Logical IO Number
dcmECIONum OBJECT-TYPE
 SYNTAX DcmLogIONum
 ACCESS read-only
 STATUS mandatory
 DESCRIPTION
 "Refer to DcmLogIONum for description."
::= {dcmEventConfigEntry 4}

-- 2.8.20.6 Logical IO State
dcmLogicalIOState OBJECT-TYPE
 SYNTAX   INTEGER 
 {
  other (1),
  on (2),
  off (3),
  weight (4),
  pulsed (5),
  triggered (6),
  valueA-D (7)
 }
 ACCESS   read-write
 STATUS   mandatory
 DESCRIPTION
 "This field defines the specific logical IO states (e.g., on, off,  etc) that are used to determine if an event has occurred.    The values are:
other (1) – not defined below
on (2) – Logical IO has turned on.
off (3) – Logical IO has turned off.
weight (4) – This event record represents a raw weight.
pulsed (5) – Logical IO has been pulsed.
triggered (6) – Logical IO has been triggered.
valueA-D (7) – This event record represents a raw analog to digital count."
::= {dcmEventConfigEntry 5}

-- 2.8.20.7 Event Value Size
dcmEventValueSize OBJECT-TYPE
 SYNTAX   INTEGER (0..255)
 ACCESS   read-only
 STATUS   mandatory
 DESCRIPTION
 "This object identifies the number of bits necessary to store a value associated with this event (e.g., weight, A/D value,  etc….) that is to be recorded within the data structure.  This object shall be set by the equipment based on the logical IO associated to this event.  Note that this size can be different for each logical IO.
If the value is set to zero (0), no value field is contained in the data structure for this event."
::= {dcmEventConfigEntry 6}

-- 2.8.20.8 Timestamp Size
dcmTimestampSize OBJECT-TYPE
 SYNTAX   INTEGER (0..255)
 ACCESS   read-only
 STATUS   mandatory
 DESCRIPTION
 "This object identifies the number of bits used to record the timestamp of an event within the data structure. The time stamp of an event is referenced to the start of the study or a timer event, whichever occurred last. If the value is set to zero (0), no timestamp field is contained in the data structure.
The time stamp resolution associated with this dcmECStudyNum is calculated by (dcmTimerEventMaxPeriod / (2^(dcmTimestampSize)))."
::= {dcmEventConfigEntry 7}

-- 2.8.20.9 Event Configuration Table Row Admin
dcmEventConfigRowAdmin OBJECT-TYPE
 SYNTAX   DcmRowStatus 
 ACCESS   read-write
 STATUS   mandatory
 DESCRIPTION
 "allows management of the parameters used to configure an event study (this row of this table).  The SYNTAX definition allows to create, delete, disable, or edit the row."
::= {dcmEventConfigEntry 8}

-- 2.8.21 Maximum Number Of Data Recording Enable Table Rows
dcmDRETMaxNumRows OBJECT-TYPE
 SYNTAX DcmMaxNumRows
 ACCESS read-only
 STATUS mandatory
 DESCRIPTION
 "Indicates the maximum number of rows allowed for the Data Recording Enable Table."
::= {dcmStudyDataSetup 21}

-- 2.8.22 Current Number Of Data Recording Enable Table Rows
dcmDRETCurNumRows OBJECT-TYPE
 SYNTAX DcmCurNumRows
 ACCESS read-only
 STATUS mandatory
 DESCRIPTION
 "Indicates the current number of rows existing in the Data Recording Enable Table."
::= {dcmStudyDataSetup 22}

-- 2.8.23 Data Recording Enable Table 
dcmDRETable OBJECT-TYPE
 SYNTAX SEQUENCE OF DcmDREEntry
 ACCESS not-accessible
 STATUS optional
 DESCRIPTION
 "This table is single-indexed by study number.  It is used to control and read the state of each data recording study. The device must ensure that there exists an entry in this table for each data recording study defined in the Study Configuraton Table. A 'data recording study' is defined as any study that has been entered into the Study Configuration Table that has a 'Study File Index' greater than 0. If a study is deleted from the Study Configuration Table, the device shall also delete it from this table."
::= {dcmStudyDataSetup 23}

dcmDREEntry OBJECT-TYPE
 SYNTAX DcmDREEntry 
 ACCESS not-accessible
 STATUS mandatory
 DESCRIPTION "..."
 INDEX  {dcmDREStudyNum}
::= {dcmDRETable 1}

DcmDREEntry ::= SEQUENCE
{
 dcmDREStudyNum DcmStudyNum,
 dcmDREStatus   INTEGER,
 dcmDREControl  INTEGER
}

-- 2.8.23.1 Study Number
dcmDREStudyNum OBJECT-TYPE
 SYNTAX DcmStudyNum
 ACCESS read-only
 STATUS mandatory
 DESCRIPTION
 "Indicates the only index into this table. It represents a unique number for each study that is defined within the device in the dcmStudyConfigTable.  Refer to DcmStudyConfig for more detail."
::= {dcmDREEntry 1}

-- 2.8.23.2 Data Recording Enable Status
dcmDREStatus OBJECT-TYPE
 SYNTAX INTEGER 
 {
  other (1),
  idle (2),
  primed (3),
  recording (4),
  validating (5),
  error (6)
 }
 ACCESS read-only
 STATUS mandatory
 DESCRIPTION
 "Indicates the status of this study.  The values are:
- other (1),= Not defined below.
- idle (2),= The device is currently not recording any data for this study to a file.
- primed (3),= The device is waiting to start recording data to a file (either for the next even recording interval or a scheduled date/time).
- recording (4),= The device is currently recording data to the specified file for this study.
- validati\ng (5),= The device is currently validating the configured study. The device can only be in this state if the value of the dcmDREControl object has been set to 'validate' or 'prime'.
 - error (6)= Indicates any error associated with this study including invalid configuration setups.  The dcmErrCodeTable should be checked to determine which objects caused the errors."
::= {dcmDREEntry 2}

-- 2.8.23.3 Data Recording Control
dcmDREControl OBJECT-TYPE
 SYNTAX INTEGER 
 {
  prime (1), 
  quitRecording (2),
  validate (3)
 }
 ACCESS read-write
 STATUS mandatory
 DESCRIPTION
 "This object allows a user to command the device to:
-prime – Sets device into a state where it is waiting to begin data recording (typically waiting for the start of the next even recording interval or some scheduled start date/time).  The device shall perform a validation before going to primed.  If there are no errors, the device shall go into the primed state.  If there are errors, the device shall indicate 'error' in the dcmDREStatus object.  The dcmErrCodeTable should be checked for which objects caused the errors.
-quitRecording – The device shall stop collecting and storing data to the data files.  This can be used when the device is either in the 'primed' mode or 'recording' mode as indicated by the Data Recording Status field in this table.
-validate – Commands the device to perform a validation of the current study settings for the specified study.  This control option is only valid when the device is in idle or error mode as indicated by the Data Recording Enable Status object.  If the Data Recording Status field is set to error after performing the validation, the dcmErrCodeTable should be checked to determine which object caused the errors.  The dcmDREStatus object shall be set to either idle or error after the validation is finished.  A GET on this object shall return the value of the last user-selected control."
::= {dcmDREEntry 3}

-- 2.8.24 Maximum Number Of Monitor Enable Table Rows
dcmMETMaxNumRows OBJECT-TYPE
 SYNTAX DcmMaxNumRows
 ACCESS read-only
 STATUS mandatory
 DESCRIPTION
 "Indicates the maximum number of rows allowed for the Monitor Enable Table."
::= {dcmStudyDataSetup 24}

-- 2.8.25 Current Number Of Monitor Enable Table Rows
dcmMETCurNumRows OBJECT-TYPE
 SYNTAX DcmCurNumRows
 ACCESS read-only
 STATUS mandatory
 DESCRIPTION
 "Indicates the current number of rows existing in the Monitor Enable Table."
::= {dcmStudyDataSetup 25}

-- 2.8.26 Monitor Enable Table
dcmMETable OBJECT-TYPE
 SYNTAX SEQUENCE OF DcmMEEntry
 ACCESS not-accessible
 STATUS optional
 DESCRIPTION
 "This table is single-indexed by study number.  
It is used to control and read the state of each 'Monitor Study'.
A Binned Monitor Study shall return the bin counts for the current recording interval as defined by the 'Data' column of the Data Structure Table for Binned Data (note that in asciiData Monitor Modes, the number of octets per binned count is not sent).
A PVR Monitor Study shall return one or more PVR/s as defined by the 'Data' column of the Data Structure Table for PVR Data (note that in asciiData Monitor Modes, the dcm device may translate the vehicle time tag to a more user friendly format (e.g. 'mm/dd/yy hh:mm:ss').
An Event Monitor Study shall return one or more sensor events (Logical IO Events) as defined by the 'Data' column of the Data Structure Table for Event Data (note that in asciiData Monitor Modes, the ascii hex representation of each event record field will be sent since event records are defined in bits).
The 'Data' column of the Data Structure Table is an OCTET STRING, it will contain the length of the data returned by the device for each type of Monitor Mode 2 (binary data).  The OCTET STRING identifier and length field is not included for asciiData Monitor Modes.  
Note that it may possible for vehicles or sensor events (Logical IO events) to be missed if the device does not have sufficient buffer space to hold the data before being polled (specifically in Monitor Mode 2).  This should only occur with either PVR or Event Monitor Studies.  There currently is no mechanism to notify the central application that a data over-run has occurred.  The best approach (if possible) would be to use Monitor Mode 1 allowing the device to stream out the data as it occurs.  This however requires that the central application can keep up with the streamed data.
Monitor Studies are typically used to verify operation of sensors and sensor arrays.
For example, if the data in collected data files appear to be invalid, a user may want to configure an 'Event Monitor Study' (in the Study Configuration Table) that incorporates the same sensors in which the invalid data has been produced by.  The user would then enable the 'Event Monitor Mode' from within this table.  The user would examine the event data returned by the device to determine if all of the specified sensors appear to be operating correctly.
Monitor Studies are typically turned on for a short period of time and then disabled.  The data is sent to a hardware communications port and not saved to a data file.
The study specified in this table must point to a 'Monitor Study'.  A 'Monitor Study' is defined as any study that has been configured in the Study Configuration Table with it's 'Study File Index' set to 0. 
The asciiData Monitor Modes are intended to provide user-readable output without interpretation and is included for historical purposes.
The Row Admin field is not required in this table.  If a study is deleted from the Study Configuration Table, the device shall also delete any row associated with the same study number from this table."
::= {dcmStudyDataSetup 26}

dcmMEEntry OBJECT-TYPE
 SYNTAX DcmMEEntry 
 ACCESS not-accessible
 STATUS mandatory
 DESCRIPTION "..."
 INDEX  {dcmMEStudyNum}
::= {dcmMETable 1}

DcmMEEntry ::= SEQUENCE
{
 dcmMEStudyNum     DcmStudyNum,
 dcmMEIONum        DcmLogIONum,
 dcmMEType         INTEGER,
 dcmMETimeInterval INTEGER,
 dcmMEControl      INTEGER,
 dcmMEStatus       INTEGER,
 dcmMEPollNow      OCTET STRING
}

-- 2.8.26.1 Study Number
dcmMEStudyNum OBJECT-TYPE
 SYNTAX DcmStudyNum
 ACCESS read-only
 STATUS mandatory
 DESCRIPTION
 "Indicates the only index into this table. It represents a unique number for the specified Monitor Study that is configured within the dcmStudyConfigTable."
::= {dcmMEEntry 1}

-- 2.8.26.2 Logical IO Number
dcmMEIONum OBJECT-TYPE
 SYNTAX DcmLogIONum
 ACCESS read-write
 STATUS mandatory
 DESCRIPTION
 "Identifies which hardware communications port to which the Monitor Mode data shall be sent.  Refer to DcmLogIONum for more detail."
::= {dcmMEEntry 2}	

-- 2.8.26.3 Monitor Enable Type
dcmMEType OBJECT-TYPE
 SYNTAX INTEGER 
 {
  other (1),
  asciiData (2),
  binaryData (3)
 }
 ACCESS read-write
 STATUS mandatory
 DESCRIPTION
 "Indicates the encoding of the data packet returned by the device.  The values are:
-other(1)=not defined.

-asciiData(2)=data packet is encoded using an ascii representation of the 'Data' column of the Data Structure Table.  This mode of operation is intended to provide the user with readable data directly from the device without requiring interpretation (it is included for historical purposes).  Each field of the data packet (a defined bin for a binned study, a pvr parameter for a pvr study, or each field of an event record for an event study) shall be separated by a 'white space' (either an ascii space, ascii comma, ascii tab).  Each record (all of the binned counts for a binned study, each set of vehicle parameters for a pvr study and each logical IO event record for an event study), will be terminated by a 'white terminator' (an ascii carriage return, an ascii line feed or a combination ascii carriage return/line feed). Because each field is separated by an ascii 'white space', the dcn device may choose to pad each field with leading ascii zeros (ascii code h30) to make each identical field the same length for readability.  The octet string code (04h) and the length of the octet string fields are not sent in asciiData mode.  The number of octets per binned counts for binned studies is not sent.  The vehicle time tag for pvr studies may be translated by before being sent. The data fields sent for event studies shall be the ascii hex representation of each defined field since event records are defined in bits.

-binaryData(3)=data packet is encoded in binary.  The data is encoded as defined by the 'Data' field of the Data Structure Table for the specified type of data."
::= {dcmMEEntry 3}

-- 2.8.26.4 Monitor Enable Time Interval
dcmMETimeInterval OBJECT-TYPE
 SYNTAX INTEGER (0..255)
 ACCESS read-write
 STATUS mandatory
 DESCRIPTION
"Indicates the time (in seconds) between the sending of each data packet for the specified Monitor Mode.  This column is only valid for Monitor Mode 1 configurations, it shall be ignored for Monitor Mode 2.
Setting this to 0 shall cause the device to send a data packet for every occurrence of the specified study type data, (PVR Monitor Mode – a data packet shall be sent for each vehicle that traverses the associated sensor array/s, Event Monitor Mode – a data packet shall be sent for each change of state of the associated sensor/s, Binned Monitor Mode – 0 shall not be a valid option, the device shall return an error code of 'invalidOption' as the result of a 'validate'."
::= {dcmMEEntry 4}

-- 2.8.26.5 Monitor Enable Control
dcmMEControl OBJECT-TYPE
 SYNTAX INTEGER 
 {
  validate (1),
  enableMon1 (2),
  enableMon2 (3),
  disableMon (4)
 }
 ACCESS read-write
 STATUS mandatory
 DESCRIPTION
 "This object allows a user to command the device to:
-validate – Commands the device to perform a validation of the current study settings for the specified study.  If the Monitor Enable Status field is set to error after performing the validation, the dcmErrCodeTable should be checked to determine which object caused the errors.  
-enableMon1On – Commands the device to enable Monitor Mode 1 (refer to dcmMEStatus for a description of Monitor Mode 1).  If a validation of the specified study hasn't been performed yet, the device shall perform a validation.  After the validation, this study shall either be in error, idle or a Monitor Mode On state.  If an error occurs, the application should check the dcm Error Code table (dcmErrCodeTable) for more information regarding the errors.
-enableMon2On – Commands the device to enable Monitor Mode 2 (see dcmMEStatus for a description of Monitor Mode 2).  If a validation of the specified study hasn't been performed yet, the device shall perform a validation.  After the validation, this study shall either be in error, idle or a Monitor Mode On state.  If an error occurs, the application should check the dcm Error Code table (dcmErrCodeTable) for more information regarding the errors.
-disableMon – Commands the device to disable Monitor Mode.
A GET on this object shall return the value of the last user-selected control."
::= {dcmMEEntry 5}

-- 2.8.26.6 Monitor Enable Status
dcmMEStatus OBJECT-TYPE
 SYNTAX INTEGER 
 {
  other (1),
  error (2),
  validating (3),
  monitorMode1On (4),
  monitorMode2On (5),
  idle(6)
 }
 ACCESS read-only
 STATUS mandatory
 DESCRIPTION
 "Indicates the status of this study.  The values are:
- other (1) = Not defined below.
- error (2) = There was an error in the 'Monitor Study' found by the device when it was commanded to enable a Monitor Mode.  Check the dcm Error Code Table (dcmErrCodeTable) for more information regarding the error.
- validating (3) = The device is currently validating the configured study. The device can only be in this state if the value of the dcmDREControl object has been set to 'validate' or a Monitor Mode was enabled. 
- monitorMode1On (4)= Indicates that the device has successfully enabled Monitor Mode 1.  Monitor Mode 1 is an asynchronous mode of operation where the device shall asynchronously stream out data packets (as defined by the 'Data' field in the Data Structure Table for the specified study) without any protocol wrapper.  The time between the device sending each data packet is defined by dcmMETimeInterval.
This mode should only be enabled in a point to point communications architecture since there is no protocol wrapper around the streamed data. This mode has been included for compatibility with existing systems.  
- monitorMode2On (5) = Indicates that the device has successfully enabled Monitor Mode 2.  Monitor Mode 2 is a synchronous mode of operation in which each data packet must be polled for by the application.  The encoding of each data packet shall be defined by the 'Data' field of the Data Structure Table for the specified type of study) The dcmMEPollNow column in this row shall be used to poll for each data packet.  Each time the application performs a 'Get' on the dcmMEPollNow column, the device shall respond by sending a data packet. The data packet shall contain all of the associated data from the time of the last poll up to the current time.  
- idle (6) = No Monitor Modes are enabled."
::= {dcmMEEntry 6}

-- 2.8.26.7 Monitor Enable Poll Now
dcmMEPollNow OBJECT-TYPE
 SYNTAX OCTET STRING
 ACCESS read-only
 STATUS mandatory
 DESCRIPTION
 "This column is only valid for Monitor Mode 2.  Anytime an application performs a 'GET' on this column, the device shall respond by sending back a data packet (as defined by the 'Data' column of the 'Data Structure Table' for the specified study).  If Monitor Mode 2 is not enabled for this Monitor Study, the device shall respond with an OCTET STRING of size 0 octets."
::= {dcmMEEntry 7}

-- 2.8.27 Array Parameter Change Record Table 
dcmAPCTable OBJECT-TYPE
 SYNTAX   SEQUENCE OF DcmAPCEntry
 ACCESS   not-accessible
 STATUS   optional
 DESCRIPTION
"This table has been defined to specify a data structure record format for any array parameter changes that need to be written to the dcmDataStructureTable, it is not accessible by the central application.  The time tag column has been defined as the index for syntax purposes only, there really are no indexes for this table.
Since this table represents raw data, each column of this table shall be stored in the 'data' column of the dcmDataStructureTable using the encoding specified by the 'File Encoding Code' in the 'File Parameter Table' for this study."
::= {dcmStudyDataSetup 27}

dcmAPCEntry OBJECT-TYPE
 SYNTAX   DcmAPCEntry 
 ACCESS   not-accessible
 STATUS   mandatory
 DESCRIPTION "..."
 INDEX    {dcmAPCTimeTag}
::= {dcmAPCTable 1}

DcmAPCEntry ::= SEQUENCE 
{
 dcmAPCTimeTag  DcmTimeTagIndex,  
 dcmAPCArrNum   DcmArrayNum,
 dcmAPCType     DcmArrayParamType,
 dcmAPCValue    DcmArrayParamValue,
 dcmAPCFileName DcmArrayParamFileName
}	

-- 2.8.27.1 Time Tag
dcmAPCTimeTag OBJECT-TYPE
 SYNTAX   DcmTimeTagIndex
 ACCESS   read-only --This object is not intended to be accessed,
                    -- the SMIC compiler won't allow all objects of 
                    -- a table to be defined as 'non-accessible',
                    -- so this object was set to be 'read-only'.
 STATUS   mandatory
 DESCRIPTION
 "Defines the time at which the specified array parameter change occurred.  The value of this object follows the 'controller-localTime' setup, which specifies the epoch since Midnight January 1, 1970."
::= {dcmAPCEntry 1}

-- 2.8.27.2 Array Number
dcmAPCArrNum OBJECT-TYPE
 SYNTAX DcmArrayNum
 ACCESS   not-accessible
 STATUS   mandatory
 DESCRIPTION
 "Refer to DcmArrayNum for a more detailed description."
::= {dcmAPCEntry 2}

-- 2.8.27.3 Array Parameter Type
dcmAPCType OBJECT-TYPE
 SYNTAX DcmArrayParamType
 ACCESS   not-accessible
 STATUS   mandatory
 DESCRIPTION
 "Indicates the type of parameter associated with an array. One or more types can be associated with an array.  
Refer to DcmArrayParamType for a more detailed description."
::= {dcmAPCEntry 3}

-- 2.8.27.4 Array Parameter Value
dcmAPCValue OBJECT-TYPE
 SYNTAX   DcmArrayParamValue
 ACCESS   not-accessible
 STATUS   mandatory
 DESCRIPTION
 "Indicates the value associated with a particular array parameter type as specified by the dcmAPCType column.  Refer to DcmArrayParamValue for a more detailed description."
::= {dcmAPCEntry 4}

-- 2.8.27.5 Array Parameter FileName Pointer
dcmAPCFileName OBJECT-TYPE
 SYNTAX   DcmArrayParamFileName
 ACCESS   not-accessible
 STATUS   mandatory
 DESCRIPTION
 "Indicates a file name that contains the array parameter calibration information. This column shall always be set to a NULL (using the encoding specified by the 'File Encoding Code' in the 'File Parameter Table' for this study) unless the value of dcmAPCType is set to 'calFilPointer'.  Refer to DcmArrayParamFileName for a more detailed description."
::= {dcmAPCEntry 5}

-- 2.8.28 Logical IO Parameter Change Record Table 
dcmIOPCRecTable OBJECT-TYPE
 SYNTAX   SEQUENCE OF DcmIOPCRecEntry
 ACCESS   not-accessible
 STATUS   optional
 DESCRIPTION
 "This table has been defined to specify a data structure record format for any IO parameter changes that need to be written to the dcmDataStructureTable, it is not accessible by the central application.  The time tag column has been defined as the index for syntax purposes only, there really are no indexes for this table.
Since this table represents raw data, each column of this table shall be stored in the 'data' column of the dcmDataStructureTable using the encoding specified by the 'File Encoding Code' in the 'File Parameter Table' for this study."
::= {dcmStudyDataSetup 28}

dcmIOPCRecEntry OBJECT-TYPE
 SYNTAX   DcmIOPCRecEntry 
 ACCESS   not-accessible
 STATUS   mandatory
 DESCRIPTION "..."
 INDEX   {dcmIOPCTimeTag}
::= {dcmIOPCRecTable 1}

DcmIOPCRecEntry  ::= SEQUENCE 
{
 dcmIOPCTimeTag   DcmTimeTagIndex,
 dcmIOPCNum       DcmLogIONum,
 dcmIOPCParamTyp  DcmIOParamType,
 dcmIOPCParamVal  DcmIOParamValue
}

-- 2.8.28.1 IOPC Time Tag
dcmIOPCTimeTag OBJECT-TYPE
 SYNTAX   DcmTimeTagIndex
 ACCESS   read-only --This object is not intended to be accessed, 
                    -- the SMIC compiler won't allow all objects of 
                    -- a table to be defined as 'non-accessible',
                    -- so this object was set to be 'read-only'.
 STATUS   mandatory
 DESCRIPTION
 "Defines the time at which the specified logical IO parameter change occurred.  The value of this object follows the 'controller-localTime' setup, which specifies the epoch since Midnight January 1, 1970."
::= {dcmIOPCRecEntry 1}

-- 2.8.28.2 IOPC Logical IO Number
dcmIOPCNum OBJECT-TYPE
 SYNTAX DcmLogIONum
 ACCESS not-accessible
 STATUS mandatory
 DESCRIPTION
 "Refer to DcmLogIONum for description."
::= {dcmIOPCRecEntry 2}

-- 2.8.28.3 IOPC IO Parameter Type
dcmIOPCParamTyp OBJECT-TYPE
 SYNTAX DcmIOParamType
 ACCESS not-accessible
 STATUS mandatory
 DESCRIPTION
 "Refer to DcmIOParamType for description."
::= {dcmIOPCRecEntry 3}

-- 2.8.28.4 IOPC IO Parameter Value
dcmIOPCParamVal OBJECT-TYPE
 SYNTAX DcmIOParamValue
 ACCESS not-accessible	
 STATUS mandatory
 DESCRIPTION
 "Refer to DcmIOParamValue for description."
::= {dcmIOPCRecEntry 4}

-- 2.8.29 Log Data Record Table 
dcmLDRecTable OBJECT-TYPE
 SYNTAX   SEQUENCE OF DcmLDRecEntry
 ACCESS   not-accessible
 STATUS   optional
 DESCRIPTION
 "This table has been defined to specify a data structure record format for any log data that need to be written to the dcmDataStructureTable, it is not accessible by the central application.  The time tag column has been defined as the index for syntax purposes only, there really are no indexes for this table.
Since this table represents raw data, each column of this table shall be stored in the 'data' column of the dcmDataStructureTable using the encoding specified by the 'File Encoding Code' in the 'File Parameter Table' for this study."
::= {dcmStudyDataSetup 29}

dcmLDRecEntry OBJECT-TYPE
 SYNTAX   DcmLDRecEntry 
 ACCESS   not-accessible
 STATUS   mandatory
 DESCRIPTION "..."
 INDEX   {dcmLDTimeTag}
::= {dcmLDRecTable 1}

DcmLDRecEntry ::= SEQUENCE 
{
 dcmLDTimeTag   DcmTimeTagIndex,
 dcmLDData      OCTET STRING
}

-- 2.8.29.1 Time Tag
dcmLDTimeTag OBJECT-TYPE
 SYNTAX   DcmTimeTagIndex
 ACCESS   read-only --This object is not intended to be accessed, 
                    -- the SMIC compiler won't allow all objects of 
                    -- a table to be defined as 'non-accessible',
                    -- so this object was set to be 'read-only'.
 STATUS   mandatory
 DESCRIPTION
 "Defines the time at which the specified data log occurred.  The value of this object follows the 'controller-localTime' setup, which specifies the epoch since Midnight January 1, 1970."
::= {dcmLDRecEntry 1}

-- 2.8.29.2 Log Data
dcmLDData OBJECT-TYPE
 SYNTAX   OCTET STRING
 ACCESS   not-accessible
 STATUS   mandatory
 DESCRIPTION
 "This field contains the actual log data that was written to the data file as an octet string with no encoding."
::= {dcmLDRecEntry 2}

-- 2.8.30 Data Structure Table 
dcmDataStructureTable OBJECT-TYPE
 SYNTAX   SEQUENCE OF DcmDataStructureEntry
 ACCESS   not-accessible
 STATUS   optional
 DESCRIPTION
 "This is a doubly-indexed table.  It defines how the data for each type of study (binned, pvr, event) shall be stored within the data files.  This table is not accessible to any application.  It's purpose is to define a data structure for decoding purposes within the data files.  The 2nd index is used as a count (sequence number) associated with the Data Structure Table.  When the application is decoding the data, it can use the 2nd index to verify if  the data file contains all of the data packets for a specified study (2nd index is sequential with no missing numbers for the specified study)."
::= {dcmStudyDataSetup 30}

dcmDataStructureEntry OBJECT-TYPE
 SYNTAX   DcmDataStructureEntry 
 ACCESS   not-accessible
 STATUS   mandatory
 DESCRIPTION "..."
 INDEX {dcmDSStudyNum, dcmDataStrucIndex}
::= {dcmDataStructureTable 1}

DcmDataStructureEntry ::= SEQUENCE 
 {
  dcmDSStudyNum     DcmStudyNum,
  dcmDataStrucIndex INTEGER, 
  dcmStartTime      Counter,
  dcmEndTime        Counter,
  dcmDataNumRecords INTEGER,
  dcmDataEncoding   INTEGER,
  dcmData           OCTET STRING
 }

-- 2.8.30.1 Study Number
dcmDSStudyNum OBJECT-TYPE
 SYNTAX DcmStudyNum
 ACCESS   read-only --This object is not intended to be accessed, 
                    -- the SMIC compiler won't allow all objects of 
                    -- a table to be defined as 'non-accessible',
                    -- so this object was set to be 'read-only'.
 STATUS mandatory
 DESCRIPTION
 "Indicates the first index into this table. It represents a unique number for each study that is defined within the device in the dcmStudyConfigTable.  Refer to DcmStudyConfig for more detail."
::= {dcmDataStructureEntry 1}

-- 2.8.30.2 Data Structure Table Index
dcmDataStrucIndex OBJECT-TYPE
 SYNTAX INTEGER (1..255)
 ACCESS not-accessible
 STATUS mandatory
 DESCRIPTION
 "Indicates the second index into this table.  The 2nd index is used as a count (sequence number) associated with the Data Structure Table.  When the application is decoding the data, it can use the 2nd index to verify if  the data file contains all of the data packets (2nd index is sequential with no missing numbers)."
::= {dcmDataStructureEntry 2}

-- 2.8.30.3 Start time associated with the data in this packet
dcmStartTime OBJECT-TYPE
 SYNTAX Counter
 ACCESS not-accessible
 STATUS mandatory
 DESCRIPTION
 "Defines the start date/time of the data contained within the data portion of this packet. The value of this object follows the 'controller-localTime' setup, which specifies the epoch since Midnight January 1, 1970."
::= {dcmDataStructureEntry 3}

-- 2.8.30.4 End time associated with the data in this packet
dcmEndTime OBJECT-TYPE
 SYNTAX   Counter
 ACCESS   not-accessible
 STATUS   mandatory
 DESCRIPTION
 "Defines the end date/time of the data contained within the data portion of this packet.  The value of this object follows the 'controller-localTime' setup, which specifies the epoch since Midnight January 1, 1970."
::= {dcmDataStructureEntry 4}

-- 2.8.30.5 Number of records encoded in the data section of this table
dcmDataNumRecords OBJECT-TYPE
 SYNTAX   INTEGER (0..16777215)
 ACCESS   not-accessible
 STATUS   mandatory
 DESCRIPTION
 "This field contains the number of records contained in the data section of this table.  A binned study record consists of the specified data (as defined in the Bin Relation Table) for a single recording interval.  A Pvr study record is defined as the grouping of the user-defined parameters (Pvr Study Configuration Table) for each vehicle that traverses any array in the specified study.  An event record consists of the grouping of bits (as defined in the Event Study Configuration Table and the Event To Logical IO Mapping Table) for each IO activation associated with this study.  If there is no data associated with the specified data packet (e.g. no vehicles traversed the sensor arrays during that time period), the number of records field shall be set to 0 and the data field shall be set to an OCTET STRING of length 0."
::= {dcmDataStructureEntry 5}

-- 2.8.30.6 Data Encoding Code
dcmDataEncoding OBJECT-TYPE
 SYNTAX   INTEGER
 { 
  other (1),
  noEncoding (2)
 }
 ACCESS   not-accessible
 STATUS   mandatory
 DESCRIPTION
 "This field contains a code which specifies the encoding of the data packet.  Currently no encodings have been defined.  This field is for future enhancements (e.g. data compression)."
::= {dcmDataStructureEntry 6}

-- 2.8.30.7 Collected Data
dcmData OBJECT-TYPE
 SYNTAX   OCTET STRING
 ACCESS   not-accessible
 STATUS   mandatory
 DESCRIPTION
 "This field contains the actual data that was recorded for this study.  Although it is defined as an Octet String, it represents binary data.  The type of data encoded in this column is identified in the configured study mapped to this row of this table (refer to Study Configuration Table).

Binned data shall store a single octet value as the first byte in this field which indicates the number of octets used to store each bin count.  The number and order of the bin counts stored are defined by the Binned Study Configuration Table (refer to Binned Data Bins Ordering C.3.1.8).  Each recording interval is considered a binned data record.  One or more binned data records may be stored in this field as specified by the number of records field in this row of this table.  

PVR data shall be stored as defined by the PVR Study Configuration Table.  The PVR data (as defined in the PVR Study Configuration Table) associated with each vehicle is considered a vehicle record.  One or more vehicle records may be stored in this field as specified by the number of records field in this row of this table.

Event data shall be stored as defined by the Event Study Configuration Table.  Each sensor event shall be considered an event record.  One or more event records may be stored in this field as specified by the number of records field in this row of this table.

ArrayParam data shall be stored as defined by the Array Parameter Change Record Table.  It represents Array Parameters (refer to the Array Parameter Table) that have been changed in the dcm device either manually or automatically.  One or more Array Parameter Change Records may be stored in this field as specified by the number of records field in this row.

LogicalIOParam data shall be stored as defined by the Logical IO Parameter Change Record Table. It represents Logical IO Parameters (refer to the Logical IO Parameter Table) that have been changed in the dcm device either manually or automatically. One or more Logical IO Parameter Change Records may be stored in this field as specified by the number of records field in this row.

LogData data shall be stored as defined by the Log Data Record Table.  It represents information (as an octet string) with a time tag which the dcm device has written to the data file.  One or more Log Records may be stored in this field as specified by the number of records field in this row.

Refer to Annex C.3.1 for an example of Binned Record Data encoding, Annex C.3.2 for an example of PVR Record Data encoding and Annex C.3.3 for an example of Event Record Data encoding. This packet may contain data for one or more recording intervals.  The length of the entire data section shall be encoded  as the length field of this Octet String.  If there is no data associated with the specified data packet (e.g. no vehicles traversed the sensor arrays during that time period), the number of records field shall be set to 0 and an ASN.1 NULL shall be placed in the data field."
::= {dcmDataStructureEntry 7}

-- 2.9 FILE SETUP NODE 
--dcm File Configuration Node
dcmFileConfig OBJECT IDENTIFIER ::= {dcm 7}
-- This node is an identifier used to group all objects for configuring of the 
-- file parameters that are common to data collection and monitoring 
-- devices.

-- 2.9.1 Current Number Of File Structures
dcmNumFileStructures   OBJECT-TYPE
 SYNTAX  INTEGER (0..255)
 ACCESS  read-only
 STATUS  optional
 DESCRIPTION
 "indicates the current number of defined file structures in the File Structure Table."
::= {dcmFileConfig 1}

-- 2.9.2 Maximum Number Of File Structure Table Rows
dcmFSTMaxNumRows OBJECT-TYPE
 SYNTAX DcmMaxNumRows
 ACCESS read-only
 STATUS mandatory
 DESCRIPTION
 "Indicates the maximum number of rows allowed for the File Structure Table."
::= {dcmFileConfig 2}

-- 2.9.3 Current Number Of File Structure Table Rows
dcmFSTCurNumRows OBJECT-TYPE
 SYNTAX DcmCurNumRows
 ACCESS read-only
 STATUS mandatory
 DESCRIPTION
 "Indicates the current number of rows existing in the File Structure Table."
::= {dcmFileConfig 3}

-- 2.9.4 File Structure Table
dcmFileStrucTable OBJECT-TYPE
 SYNTAX SEQUENCE OF DcmFileStrucEntry
 ACCESS not-accessible
 STATUS optional
 DESCRIPTION
 "This is a doubly-indexed table. It defines which items shall be stored in the data files.  By default, the dcm MIB Version Number object shall always be included as the first object.  The device shall also include the required data packets (encoded as Data Structure Tables) for the included studies.    The objects specified in this table shall be stored in the data file in the same order as specified in this table.  There may be other objects included in the header information section that have not been specified in this table, however these object can be skipped over by using the length field of the OID and the length field of the associated Value."
::= {dcmFileConfig 4}

dcmFileStrucEntry OBJECT-TYPE
 SYNTAX DcmFileStrucEntry 
 ACCESS not-accessible
 STATUS mandatory
 DESCRIPTION "..."
 INDEX {dcmFSFileStrucNum, dcmFileStrucIndex}
::= {dcmFileStrucTable 1}

DcmFileStrucEntry ::= SEQUENCE 
{
 dcmFSFileStrucNum    DcmFileStrucNum,
 dcmFileStrucIndex    INTEGER,	
 dcmFileStrucOID      OBJECT IDENTIFIER,
 dcmFileStrucRowAdmin DcmRowStatus
}

-- 2.9.4.1 File Structure Number
dcmFSFileStrucNum OBJECT-TYPE
 SYNTAX   DcmFileStrucNum
 ACCESS   read-only
 STATUS   mandatory
 DESCRIPTION
 "Indicates the first index into this table.  This is the number assigned to the defined file structure.  It is highly recommended that the application try to keep this number sequential (reuse numbers that have been deleted)."
::= {dcmFileStrucEntry 1}

-- 2.9.4.2 File Structure Index
dcmFileStrucIndex OBJECT-TYPE
 SYNTAX INTEGER (1..255)
 ACCESS read-only
 STATUS mandatory
 DESCRIPTION
 "Indicates the second index into this table.  A 2nd index is required to allow specifying multiple parameters to store for each File Structure Number."
::= {dcmFileStrucEntry 2}

-- 2.9.4.3 File Structure Table OID
dcmFileStrucOID OBJECT-TYPE
 SYNTAX   OBJECT IDENTIFIER
 ACCESS   read-write
 STATUS   mandatory
 DESCRIPTION
 "This field contains the OID of the object/table to include in the data file.  All OID's shall be specified using the full OID address.  Relative OID addressing is not allowed."
::= {dcmFileStrucEntry 3}

-- 2.9.4.4 File Structure Table Row Admin
dcmFileStrucRowAdmin OBJECT-TYPE
 SYNTAX   DcmRowStatus 
 ACCESS   read-write
 STATUS   mandatory
 DESCRIPTION
 "allows management of the parameters used to configure an event study (this row of this table).  The SYNTAX definition allows to create, delete, disable, or edit the row."
::= {dcmFileStrucEntry 4}


-- 2.9.5 Maximum Number Of File Parameter Table Rows
dcmFPTMaxNumRows OBJECT-TYPE
 SYNTAX DcmMaxNumRows
 ACCESS read-only
 STATUS mandatory
 DESCRIPTION
 "Indicates the maximum number of rows allowed for the File Parameter Table."
::= {dcmFileConfig 5}

-- 2.9.6 Current Number Of File Parameter Table Rows
dcmFPTCurNumRows OBJECT-TYPE
 SYNTAX DcmCurNumRows
 ACCESS read-only
 STATUS mandatory
 DESCRIPTION
 "Indicates the current number of rows existing in the Monitor Enable Table."
::= {dcmFileConfig 6}

-- 2.9.7 File Parameter Table
dcmFPTable OBJECT-TYPE
 SYNTAX SEQUENCE OF DcmFPEntry
 ACCESS not-accessible
 STATUS optional
 DESCRIPTION
 "This is a doubly-indexed table.  It links a defined study from the Study Configuration Table to a user-defined file format in the File Structure Table through the Study File Index in the Study Configuration Table.  It is recommended to include this table in the data file as one of the first objects in the data file (specify this OID in the Data File Structure Table as one of the first OID's to store) to allow determining what File Encoding was used (BER or OER) and if Relative Addressing has been enabled.  If the defined study is deleted from the Study Configuration Table, the entry for that study shall be automatically deleted from this table by the device."
::= {dcmFileConfig 7}

dcmFPEntry OBJECT-TYPE
 SYNTAX DcmFPEntry 
 ACCESS not-accessible
 STATUS mandatory
 DESCRIPTION "..."
 INDEX {dcmFPFileStudyIndex, dcmFPFileStrucNum}	
::= {dcmFPTable 1}	

DcmFPEntry ::= SEQUENCE 	
{
 dcmFPFileStudyIndex      DcmFileStudyIndex,
 dcmFPFileStrucNum        DcmFileStrucNum,
 dcmFPRecInt              INTEGER,
 dcmFPFileFreq            INTEGER,
 dcmFPLogicalIONumber     DcmLogIONum,
 dcmFPRelativeAddrFlag    INTEGER,
 dcmFPEncodingCode        INTEGER,
 dcmFPRowAdmin            DcmRowStatus
}

-- 2.9.7.1 File Study Index
dcmFPFileStudyIndex OBJECT-TYPE
 SYNTAX   DcmFileStudyIndex
 ACCESS   read-only	
 STATUS   mandatory
 DESCRIPTION
 "Indicates the first index into this table.  It defines the file structure number within the File Structure Table (non-zero values).  A value of zero (0) indicates that no data shall be recorded and the study is to be used for Monitor Modes."
::= {dcmFPEntry 1}

-- 2.9.7.2 File Structure Number
dcmFPFileStrucNum OBJECT-TYPE
 SYNTAX   DcmFileStrucNum
 ACCESS   read-only
 STATUS   mandatory
 DESCRIPTION
 "Indicates the second index into this table.  This is the number assigned to the defined file structure.  It is highly recommended that the application try to keep this number sequential (reuse numbers that have been deleted)."
::= {dcmFPEntry 2}

-- 2.9.7.3 File Recording Interval
dcmFPRecInt OBJECT-TYPE
 SYNTAX   INTEGER  (1..16777215)
 ACCESS   read-write
 STATUS   mandatory
 DESCRIPTION
 "This defines the recording interval (in seconds) for the specified study. A new row shall be created in the Data Structure Table for each recording interval. For example, if recording a binned study in 15 minute intervals (15*60 seconds), then each row of the Data Structure Table would represent 15 minutes worth of binned data.  The same would be true for pvr data and event data."
::= {dcmFPEntry 3}

-- 2.9.7.4 File Recording Frequency
dcmFPFileFreq OBJECT-TYPE
 SYNTAX INTEGER 
 {
  other (1),
  eachRecInt (2),
  hourly (3),
  daily (4),
  midnight (5),
  weekly (6),
  monthly (7),
  continuous (8)
 }
 ACCESS   read-write
 STATUS   mandatory
 DESCRIPTION
 "Indicates how frequently a new data file shall be created for the specified study.  The values are:
- other = not defined below
- eachRecInt = Creates a new data file each recording interval.
- hourly = Creates a new data file each hour (the recording interval must be set to 60 minutes or less to use this option).
- daily = Creates a new data file each day at the specified start time for this study.
- midnight = Creates a new data file each day at midnight.
- weekly = Creates a new data file each week at the specified start day of week for this study.
- monthly = Creates a new data file at the start of each calendar month.
- continuous = Creates only one data file.  All data shall be appended to the same file.  The only way to close this data file is to disable the study."
::= {dcmFPEntry 4}

-- 2.9.7.5 FP Logical IO Number
dcmFPLogicalIONumber OBJECT-TYPE 
 SYNTAX   DcmLogIONum
 ACCESS   read-write
 STATUS   mandatory
 DESCRIPTION
 "This column is used in this table to link a file to a storage memory media (which will have been assigned a logical IO number in the Physical To Logical Mapping Table.  It defines where the data files for this study shall be stored."
::= {dcmFPEntry 5}

-- 2.9.7.6 Relative Address Flag
dcmFPRelativeAddrFlag OBJECT-TYPE
 SYNTAX   INTEGER
 {
  disabled (1),
  enabled (2)
 }
 ACCESS   read-write
 STATUS   mandatory
 DESCRIPTION
 "This column is used to enable/disable the use of relative OID addressing in the specified data file.  Setting this to a 1 shall inhibit the use of relative OID addressing for this data file.  Setting this to a 2 shall enable relative OID addressing for this data file.  An application can only enable this feature.  It has no control as to where and how often (within this data file) that the device shall use this option (see dcmRelativeAddress object)."
::= {dcmFPEntry 6}

-- 2.9.7.7 File Encoding Code
dcmFPEncodingCode OBJECT-TYPE
 SYNTAX   INTEGER
 {
  other (1),
  berEncoding (2), 
  oerEncoding (3) 
 }
 ACCESS   read-write
 STATUS   mandatory
 DESCRIPTION
 "This column is used to enable various encoding schemes for the data files.  The values are:
- other = not defined below
- berEncoding = All objects shall be stored within this data file using BER encoding of the ASN.1 object definition.
- oerEncoding = All objects shall be stored within this data file using OER (Octet Encoding Rules, as defined in NTCIP 1102) encoding of the ASN.1 object definition."
::= {dcmFPEntry 7}

-- 2.9.7.8 File Parameter Table Row Admin
dcmFPRowAdmin OBJECT-TYPE
 SYNTAX   DcmRowStatus 
 ACCESS   read-write
 STATUS   mandatory
 DESCRIPTION
 "allows management of the parameters used to configure an event study (this row of this table).  The SYNTAX definition allows to create, delete, disable, or edit the row."
::= {dcmFPEntry 8}

-- 2.9.8 Data File Integrity Object
dcmDFIntegrity OBJECT-TYPE 
 SYNTAX   INTEGER  (1..65535)
 ACCESS   read-only
 STATUS   optional
 DESCRIPTION
 "The purpose of this object is to allow the device to calculate a CRC16 check on the data file for integrity and to store this within the data file (if it has been specified in the File Structure Table).  The check shall be based on all bytes of the data file except for this object. This object is read-only and cannot be manipulated by the application."
::= {dcmFileConfig 8}


-- 2.9.9 Maximum Number Of File Directory Structure Table Rows
dcmFDSTMaxNumRows OBJECT-TYPE
 SYNTAX DcmMaxNumRows
 ACCESS read-only
 STATUS mandatory
 DESCRIPTION
 "Indicates the maximum number of rows allowed for the File Directory Structure Table."
::= {dcmFileConfig 9}

-- 2.9.10 Current Number Of File Directory Structure Table Rows
dcmFDSTCurNumRows OBJECT-TYPE
 SYNTAX DcmCurNumRows
 ACCESS read-only
 STATUS mandatory
 DESCRIPTION
 "Indicates the current number of rows existing in the File Directory Structure Table."
::= {dcmFileConfig 10}

-- 2.9.11 File Directory Structure Table
dcmFileDirStrucTable OBJECT-TYPE
 SYNTAX SEQUENCE OF DcmFileDirStrucEntry
 ACCESS not-accessible
 STATUS optional
 DESCRIPTION
 "This is a doubly-indexed table. It is required to provide a consistent directory listing of data files contained within the device. The FTP directory listing command may not provide a consistent output listing of the file fields between the various FTP implementations."
::= {dcmFileConfig 11}

dcmFileDirStrucEntry OBJECT-TYPE
 SYNTAX DcmFileDirStrucEntry 
 ACCESS not-accessible
 STATUS mandatory
 DESCRIPTION "..."
 INDEX {dcmFDSLogIOIndex, dcmFDSFileNumber}
::= {dcmFileDirStrucTable 1}

DcmFileDirStrucEntry ::= SEQUENCE 
{
 dcmFDSLogIOIndex   INTEGER,
 dcmFDSFileNumber   INTEGER,
 dcmFDSFileName     OCTET STRING,
 dcmFDSStartTime    Counter,
 dcmFDSEndTime      Counter,
 dcmFDSFileSize     INTEGER,
 dcmFDSDownloadFlag INTEGER,
 dcmFDSOpenFlag     INTEGER
}

-- 2.9.11.1 Logical IO Number Index
dcmFDSLogIOIndex OBJECT-TYPE 
 SYNTAX   INTEGER  (1..255)
 ACCESS   read-only
 STATUS   mandatory
 DESCRIPTION
 "The first index is the logical IO number assigned to the memory media in which the data file is stored. The application should identify which logical IO numbers are assigned to data storage media (downloading the Physical to Logical IO Mapping Table) and use those logical IO numbers as the first index into the File Directory Structure Table, or the application can perform a getnext on the File Directory Structure Table to get the full listing of existing files."
::= {dcmFileDirStrucEntry 1}

-- 2.9.11.2 File Number
dcmFDSFileNumber OBJECT-TYPE
 SYNTAX INTEGER (1..65535)
 ACCESS read-only
 STATUS mandatory
 DESCRIPTION
 "Indicates the second index into this table.  This index is required to allow specifying multiple data files for each Logical IO storage media."
::= {dcmFileDirStrucEntry 2}

-- 2.9.11.3 File Name
dcmFDSFileName OBJECT-TYPE
 SYNTAX   OCTET STRING (SIZE (0..127))
 ACCESS   read-only
 STATUS   mandatory
 DESCRIPTION
 "This field contains the name of the data file (including any directory paths).  This name can be used in conjunction with FTP to download this data file."
::= {dcmFileDirStrucEntry 3}

-- 2.9.11.4 Start Date/Time of Data File
dcmFDSStartTime OBJECT-TYPE 
 SYNTAX   Counter
 ACCESS   read-only
 STATUS   mandatory
 DESCRIPTION
 "This field contains the start date/time for the specified data file.  The value of this object follows the 'controller-localTime' setup, which specifies the epoch since Midnight January 1, 1970."
::= {dcmFileDirStrucEntry 4}

-- 2.9.11.5 End Date/Time of Data File
dcmFDSEndTime OBJECT-TYPE 
 SYNTAX   Counter
 ACCESS   read-only
 STATUS   mandatory
 DESCRIPTION
 "This field contains the end date/time for the specified data file.  The value of this object follows the 'controller-localTime' setup, which specifies the epoch since Midnight January 1, 1970.  If the specified file is still opened, the end date/time shall indicate the devices current date/time."
::= {dcmFileDirStrucEntry 5}

-- 2.9.11.6 File Size
dcmFDSFileSize OBJECT-TYPE 	
 SYNTAX   INTEGER (0..4294967295)
 ACCESS   read-write
 STATUS   mandatory
 DESCRIPTION
 "This field is used to identify the size (in octets) of the data file.  If the file is still open, the file size shall indicate the current size of the file."
::= {dcmFileDirStrucEntry 6}

-- 2.9.11.7 File Download Flag
dcmFDSDownloadFlag OBJECT-TYPE 
 SYNTAX   INTEGER (1..255)
 ACCESS   read-write
 STATUS   mandatory
 DESCRIPTION
 "This field is used to allow the application to determine if the specified file has already been downloaded.  A file that has not been downloaded is considered to be 'new'.  It is up to the application as to how to process this field.  It could simply use a 1 to indicate the data file was downloaded or it could treat this field as a bitmap to allow multiple applications to download this file as new  by processing different bits within this field."
::= {dcmFileDirStrucEntry 7}

-- 2.9.11.8 Open Flag
dcmFDSOpenFlag OBJECT-TYPE 
 SYNTAX   INTEGER
 {
  fileOpen       (1),
  fileClosed     (2),
  fileLocked     (3),
  fileOpenLocked (4)
 }
 ACCESS   read-only
 STATUS   mandatory
 DESCRIPTION
 "This field is used to allow the application to determine if the specified file is currently open or if it has been closed by the device.  The values are:
-fileOpen =  data file is currently open (still being written to).
-fileClosed = data file has been closed by the device.
-fileLocked = data file is locked by the device, it cannot be downloaded at        this time.
-fileOpenLocked = data file is currently open and cannot be downloaded at this time (for example, may be writing to a FLASH storage media)"
::= {dcmFileDirStrucEntry 8}


-- 2.10 ERROR LOGGING NODE
--DCM Error Node
dcmErrors OBJECT IDENTIFIER ::= {dcm 8}
-- This node is an identifier used to group all errors that are common to data 
-- collection and monitoring devices.

-- 2.10.1 Maximum Number Of Error Code Table Rows
dcmECTMaxNumRows OBJECT-TYPE
 SYNTAX DcmMaxNumRows
 ACCESS read-only
 STATUS mandatory
 DESCRIPTION
 "Indicates the maximum number of rows allowed for the Error Code Table."
::= {dcmErrors 1}

-- 2.10.2 Current Number Of Error Code Table Rows
dcmECTCurNumRows OBJECT-TYPE
 SYNTAX DcmCurNumRows
 ACCESS read-only
 STATUS mandatory
 DESCRIPTION
 "Indicates the current number of rows existing in the Error Code Table."
::= {dcmErrors 2}

-- 2.10.3 Dcm Error Code Table 
dcmErrCodeTable OBJECT-TYPE
 SYNTAX SEQUENCE OF DcmErrCodeEntry
 ACCESS not-accessible
 STATUS optional
 DESCRIPTION
 "This table is a read-only table that is updated by the device after each set operation.  This table has a single general index. The index must be assigned sequentially by the device. The number of rows present are dependent on the results of the previous operation. If the last set operation resulted in no errors, then there shall be no rows configured in this table.  There can be multiple rows set (one for each item in error) or there may only be one row set which would contain the OID of the first object that was in error, this choice is implementation-specific.  Each row identifies the type of error and links it to the OID of the object that caused the dcm error. This table is NOT used to report communications protocol errors, those are handled as part of the communications protocols.  All existing rows shall be cleared out each time the device updates this table.  The rows shall always indicate errors based on the last time this table was updated and not show historical errors."
::= {dcmErrors 3}

dcmErrCodeEntry OBJECT-TYPE
 SYNTAX   DcmErrCodeEntry 
 ACCESS   not-accessible
 STATUS   mandatory
 DESCRIPTION "..."
 INDEX    {dcmErrCodeIndex}
::= {dcmErrCodeTable 1}

DcmErrCodeEntry  ::= SEQUENCE 
{
 dcmErrCodeIndex INTEGER,
 dcmErrCodeOID   OBJECT IDENTIFIER,
 dcmErrCode      INTEGER
}

-- 2.10.3.1 Error Code Index
dcmErrCodeIndex OBJECT-TYPE
 SYNTAX INTEGER (1..255)
 ACCESS read-only
 STATUS mandatory
 DESCRIPTION
 "indicates the only index into this table.  It must be assigned sequentially by the device."
::= {dcmErrCodeEntry 1}

-- 2.10.3.2 Error Code Object Identifier
dcmErrCodeOID OBJECT-TYPE
 SYNTAX OBJECT IDENTIFIER
 ACCESS read-only
 STATUS mandatory
 DESCRIPTION
 "This value points to the OID responsible for generating the error.  The OID must be specified using full OID addressing.  Relative OID addressing is not allowed."
::= {dcmErrCodeEntry 2}

-- 2.10.3.3 Dcm Error Code
dcmErrCode OBJECT-TYPE
 SYNTAX INTEGER 
 {
  other (1),
  noError (2),
  notValidAtThisTime (3),
  validationFailed (4),
  optionNotSupported (5),
  outOfRange (6),
  invalidOption (7),
  notAllowedPrimeRec (8),
  lockedOut (9),
  exceededMaxLength (10),
  exceededMaxNumberOfAllowedOccurrences (11),
  exceededMaxNumberOfRows (12),
  readOnly (13)
 }
 ACCESS read-only
 STATUS mandatory
 DESCRIPTION
 "Indicates the type of error that was detected for the object referenced by dcmErrCodeOID.  The values are:
1=other
2=noError, the operation resulted in no error for the specified object.
3=notValidAtThisTime, try to set a variable to a value that under other circumstances could be valid, but is not valid at this time (e.g. try to set RowStatus to createAndWait when it is currently set to active).
4=validationFailed, validation of a study failed.
5=optionNotSupported, (e.g. try to set an enumeration value that is not supported by the device).
6=out of range, try to set an object to a value that is out of range.
7=invalidOption (e.g. try to do axle class using standard loop loop sensor array).
8=NotAllowedPrimeRec, can't modify this object  while primed or recording
9=lockedOut, objects are currently locked (e.g. object is being modified by another application).
10=exceededMaxLength, try to set an octet string to a length greater than is supported. 
11=exceededMaxNumberOfAllowedOccurrences for this index (e.g. try to set more than the allowed number of cal factors for an IO).
12=exceededMaxNumberOfRows, allowed for this table.
13=readOnly, (e.g. try to set dataStorageMediaAvailable, this object value is read-only)."
::= {dcmErrCodeEntry 3}
-- 2.11 DCM RELATIVE ADDRESS OID OBJECT
dcmRelativeAddrOID OBJECT-TYPE
 SYNTAX   OBJECT IDENTIFIER
 ACCESS   read-write
 STATUS   optional
 DESCRIPTION
 "Indicates the OID address which shall be referenced by any object in the specified data file if relative OID's have been enabled (through the File Parameter Table). The last number indicated in the OID value shall not be repeated in the relative OID's. This object has been included to reduce overhead relative to OID's when specified in data files.  This object shall not be used to shorten OID's within SNMP messages. The device shall return an 'out of range' error if the application attempts to set this object to an OID below where this object resides.  This will prevent a situation where this object cannot be accessed anymore.  An application can only enable the usage of this object within specified data files.  Once enabled, it will be determined by the device where and how often to use it to optimize the storage requirements of OID's.  This object may be used multiple times within the same data file by the device to change the relative addressing of the OID's in order to optimize storage."
::= {dcm 9}

-- 2.12 DCM MIB VERSION NUMBER
dcmMibVersionNumber OBJECT-TYPE
 SYNTAX  INTEGER (100..65535)
 ACCESS  read-only
 STATUS  optional
 DESCRIPTION
 "Contains the version number of the dcm MIB implemented in this device, 100=version 1.00."
::= {dcm 10}


END  -- DCM-MIB1 DEFINITIONS
