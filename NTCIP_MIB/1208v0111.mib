-- 3.1	CLOSED CIRCUIT TELEVISION (CCTV) SWITCH OBJECTS

-- Filename:    1208v0111.mib
-- Description: This MIB defines those objects that are expected to be used by
--              closed circuit television (CCTV) video switching devices.
-- Source:      NTCIP 1208 v01_11d.doc
-- MIB Revision History:
-- 09/27/04     Changed name of file.
--              REMed out devices FROM TMIB-II;
--              REMed out cctvSwitch  OBJECT IDENTIFIER ::= {devices 8}
--              Added cctvSwitch FROM NTCIP8004-A-2004;
--              Changed timeDateOverlayFontNumber DEFVAL {2) to DEFVAL { ascii }
--
--              
--Copyright 2004 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--Except for the MIB, Do not copy without written permission of either AASHTO,
--ITE, or NEMA.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************

SWITCH-MIB1 DEFINITIONS ::= BEGIN

--the following OBJECT IDENTIFIERS are used in the CCTV Switch MIB:

IMPORTS
     OBJECT-TYPE
          FROM RFC-1212
--     devices 
--          FROM TMIB-II;

-- For the purpose of this section, the following OBJECT IDENTIFIERS are used:
--cctvSwitch	OBJECT IDENTIFIER ::= {devices 8}
   cctvSwitch
     FROM NTCIP8004-A-2004;

--3.2 CCTV SWITCH DISCRETE INPUT OBJECTS

cctvSwitchInput OBJECT IDENTIFIER ::= { cctvSwitch 1 }

--3.2.1 Discrete Input Status Parameter

inputStatus OBJECT-TYPE
SYNTAX	OCTET STRING (SIZE(1))
ACCESS	read-only
STATUS	mandatory
DESCRIPTION	
"<Definition> Input status denotes a bit-mapped value that indicates the current state of eight (8) user defined discrete inputs, as outlined below:
Bit7	0 = OFF, 1 = ON for the active status of discrete Input 8 (MSB),
Bit6	0 = OFF, 1 = ON for the active status of discrete Input 7,
Bit5	0 = OFF, 1 = ON for the active status of discrete Input 6,
Bit4	0 = OFF, 1 = ON for the active status of discrete Input 5,
Bit3	0 = OFF, 1 = ON for the active status of discrete Input 4,
        Bit2		0 = OFF, 1 = ON for the active status of discrete Input 3,
Bit1	0 = OFF, 1 = ON for the active status of discrete Input 2,
        Bit0		0 = OFF, 1 = ON for the active status of discrete Input 1 (LSB).
Please note that user defined discrete inputs may reduce interoperability of the device.
<DescriptiveName> CctvSwitch.inputStatus:text
<DataConceptType> Data Element"
::= {cctvSwitchInput 1}

--3.2.2 Discrete Input Latch Status Parameter

inputLatchStatus OBJECT-TYPE
SYNTAX	OCTET STRING (SIZE (1))
ACCESS	read-only
STATUS	mandatory
DESCRIPTION	
"<Definition> Latch status denotes a bit-mapped value that indicates the presence of a latched input for eight (8) user defined discrete inputs, indicating that an input has occurred since the previous latch was cleared, as outlined below:
        Bit7		0 = OFF, 1 = ON for the latch status of the discrete Input 8 (MSB),
        Bit6		0 = OFF, 1 = ON for the latch status of the discrete Input 7,
        Bit5		0 = OFF, 1 = ON for the latch status of the discrete Input 6,
        Bit4		0 = OFF, 1 = ON for the latch status of the discrete Input 5,
        Bit3		0 = OFF, 1 = ON for the latch status of the discrete Input 4,
        Bit2		0 = OFF, 1 = ON for the latch status of the discrete Input 3,
        Bit1		0 = OFF, 1 = ON for the latch status of the discrete Input 2,
        Bit0		0 = OFF, 1 = ON for the latch status of the discrete Input 1 (LSB).
Please note that user defined discrete inputs may reduce interoperability of the device.
<DescriptiveName> CctvSwitch.inputLatchStatus:text
<DataConceptType> Data Element"
::= {cctvSwitchInput 2}

--3.2.3 Discrete Input Latch Clear Parameter

inputLatchClear OBJECT-TYPE
SYNTAX	OCTET STRING (SIZE(1))
ACCESS	read-write
STATUS	mandatory
DESCRIPTION	
"<Definition> Latch clear denotes a bit-mapped value that clears the presence of a latched input for eight (8) user defined discrete inputs, as outlined below:
        Bit7		0 = OFF, 1 = ON for clearing the input latch for discrete Input 8 (MSB),
        Bit6		0 = OFF, 1 = ON for clearing the input latch for discrete Input 7,
        Bit5		0 = OFF, 1 = ON for clearing the input latch for discrete Input 6,
        Bit4		0 = OFF, 1 = ON for clearing the input latch for discrete Input 5,
        Bit3		0 = OFF, 1 = ON for clearing the input latch for discrete Input 4,
        Bit2		0 = OFF, 1 = ON for clearing the input latch for discrete Input 3,
        Bit1		0 = OFF, 1 = ON for clearing the input latch for discrete Input 2,
        Bit0		0 = OFF, 1 = ON for clearing the input latch for discrete Input 1 (LSB).
Please note that user defined discrete inputs may reduce interoperability of the device.
<DescriptiveName> CctvSwitch.inputLatchClear:text
<DataConceptType> Data Element"
::= {cctvSwitchInput 3}

--3.2.4 Discrete Input Table

inputTable OBJECT-TYPE
SYNTAX	SEQUENCE OF InputTableEntry
ACCESS	not-accessible
STATUS	mandatory
DESCRIPTION	
"<Definition> This table contains data specific to each input assignment.  Each row in the table identifies a single input assignment.  Table rows are set by the manufacturer, and row creation/deletion is not supported.  
<DescriptiveName> CctvSwitch.inputTable
<DataConceptType> Entity Type
<TableType> static"
::= {cctvSwitchInput 4}

inputTableEntry OBJECT-TYPE
SYNTAX	InputTableEntry
ACCESS	not-accessible
STATUS	mandatory
DESCRIPTION	
"<Definition> Parameters of the input table.
<DescriptiveName> CctvSwitch.inputTableEntry
<DataConceptType> Entity Type"
INDEX	{inputNumber}
::= {inputTable 1}

InputTableEntry ::= SEQUENCE {
	inputNumber			INTEGER,
	inputCameraPortNumber	INTEGER,
	inputMonitorPortNumber	INTEGER,
	inputLabelNumber		INTEGER
	}

--3.2.4.1 Discrete Input Number Parameter

inputNumber OBJECT-TYPE
SYNTAX	INTEGER (1..255)
ACCESS	read-only
STATUS	mandatory
DESCRIPTION	
"<Definition> A value representing the number of the discrete input (1 through 8).  Values of 9..255 are reserved.
<DescriptiveName> CctvSwitch.inputNumber:identifier
<DataConceptType> Data Element"
::= {inputTableEntry 1}

--3.2.4.2 Discrete Input Camera Port Number Parameter

inputCameraPortNumber OBJECT-TYPE
SYNTAX	INTEGER (0..65535)
ACCESS	read-write
STATUS	mandatory
DESCRIPTION	
"<Definition> A value representing the number of physical camera port that is associated with the discrete input.  A value of zero (0) indicates that no camera port number is associated with the discrete input.  When read, this object returns the last value written.
<DescriptiveName> CctvSwitch.inputCameraPortNumber:identifier
<DataConceptType> Data Element"
::= {inputTableEntry 2}

--3.2.4.3 Discrete Input Monitor Port Number Parameter

inputMonitorPortNumber OBJECT-TYPE
SYNTAX	INTEGER (0..65535)
ACCESS	read-write
STATUS	mandatory
DESCRIPTION	
"<Definition> A value representing the number of physical monitor port that is associated with the discrete input.  A value of zero (0) indicates that no monitor port number is associated with the input.  When read, this object returns the last value written.
<DescriptiveName> CctvSwitch.inputMonitorPortNumber:identifier
<DataConceptType> Data Element"
::= {inputTableEntry 3}


--3.2.4.4 Discrete Input Label Number Parameter

inputLabelNumber OBJECT-TYPE
SYNTAX	INTEGER (0..65535)
ACCESS	read-write
STATUS	mandatory
DESCRIPTION	
"<Definition> A value representing the label number from the switch label table that is associated with this discrete input for this monitor port.  Writing a value to this object changes the label assignment.  When read, this object returns last value written.  A value of zero (0) indicates that no input label is displayed.
<DescriptiveName> CctvSwitch.inputLabelNumber:identifier
<DataConceptType> Data Element"
::= {inputTableEntry 4}

--3.3 CCTV SWITCH DISCRETE OUTPUT OBJECTS

cctvSwitchOutput OBJECT IDENTIFIER ::= { cctvSwitch 2 }

--3.3.1 Discrete Output Status Parameter

outputStatus OBJECT-TYPE
SYNTAX	OCTET STRING (SIZE(1))
ACCESS	read-only
STATUS	mandatory
DESCRIPTION	
"<Definition> Output status denotes a bit-mapped value that indicates the current state of eight (8) user defined discrete outputs, as outlined below:
Bit7	0 = OFF, 1 = ON for the active status of discrete Output 8 (MSB),
Bit6	0 = OFF, 1 = ON for the active status of discrete Output 7,
Bit5	0 = OFF, 1 = ON for the active status of discrete Output 6,
Bit4	0 = OFF, 1 = ON for the active status of discrete Output 5,
Bit3	0 = OFF, 1 = ON for the active status of discrete Output 4,
        Bit2		0 = OFF, 1 = ON for the active status of discrete Output 3,
Bit1	0 = OFF, 1 = ON for the active status of discrete Output 2,
        Bit0		0 = OFF, 1 = ON for the active status of discrete Output 1 (LSB).
Please note that user defined discrete inputs may reduce interoperability of the device.
<DescriptiveName> CctvSwitch.outputStatus:text
<DataConceptType> Data Element"
::= {cctvSwitchOutput 1}

--3.3.2 Discrete Output Control Parameter

outputControl OBJECT-TYPE
SYNTAX	OCTET STRING (SIZE(2))
ACCESS	read-write
STATUS	mandatory
DESCRIPTION	
"<Definition> Output control activates and deactivates individual discrete outputs as outlined below:
Byte1		
	Bit7		0 = NOT SELECT, 1 = SELECT designates the control of Output 8 (MSB),
	Bit6		0 = NOT SELECT, 1 = SELECT designates the control of Output 7,
	Bit5		0 = NOT SELECT, 1 = SELECT designates the control of Output 6,
	Bit4		0 = NOT SELECT, 1 = SELECT designates the control of Output 5,
	Bit3		0 = NOT SELECT, 1 = SELECT designates the control of Output 4,
	Bit2		0 = NOT SELECT, 1 = SELECT designates the control of Output 3,
	Bit1		0 = NOT SELECT, 1 = SELECT designates the control of Output 2,
	Bit0		0 = NOT SELECT, 1 = SELECT designates the control of Output 1(LSB),
Byte2
Bit7	0 = OFF, 1 = ON for the desired active state of discrete Output 8(MSB),
Bit6	0 = OFF, 1 = ON for the desired active state of discrete Output 7,
Bit5	0 = OFF, 1 = ON for the desired active state of discrete Output 6,
Bit4	0 = OFF, 1 = ON for the desired active state of discrete Output 5,
Bit3	0 = OFF, 1 = ON for the desired active state of discrete Output 4,
Bit2	0 = OFF, 1 = ON for the desired active state of discrete Output 3,
Bit1	0 = OFF, 1 = ON for the desired active state of discrete Output 2,
Bit0	0 = OFF, 1 = ON for the desired active state of discrete Output 1(LSB).
Please note that user defined discrete inputs may reduce interoperability of the device.  When read, this object returns last value written.
<DescriptiveName> CctvSwitch.outputControl:text
<DataConceptType> Data Element"
::= {cctvSwitchOutput 2}

--3.3.3 Discrete Output Table

outputTable OBJECT-TYPE
SYNTAX	SEQUENCE OF OutputTableEntry
ACCESS	not-accessible
STATUS	mandatory
DESCRIPTION	
"<Definition> This table contains data specific to each output assignment.  Each row in the table identifies a single output assignment.  Table rows are set by the manufacturer, and row creation/deletion is not supported.
<DescriptiveName> CctvSwitch.outputTable
<DataConceptType> Entity Type
<Table Type> static"
::= {cctvSwitchOutput 3}

outputTableEntry OBJECT-TYPE
SYNTAX	OutputTableEntry
ACCESS	not-accessible
STATUS	mandatory
DESCRIPTION	
"<Definition> Parameters of the output table.
<DescriptiveName> CctvSwitch.outputTableEntry
<DataConceptType> Entity Type"
INDEX	{outputNumber}
::= {outputTable 1}

OutputTableEntry ::= SEQUENCE {
	outputNumber			INTEGER,
	outputCameraPortNumber	INTEGER,
	outputMonitorPortNumber	INTEGER,
	outputLabelNumber		INTEGER
	}

--3.3.3.1 Discrete Output Number Parameter

outputNumber OBJECT-TYPE
SYNTAX	INTEGER (1..255)
ACCESS	read-only
STATUS	mandatory
DESCRIPTION	
"<Definition> A value representing the number of the discrete output (1 through 8). Values of 9..255 are reserved.  
<DescriptiveName> CctvSwitch.outputNumber:identifier
<DataConceptType> Data Element"
::= {outputTableEntry 1}

--3.3.3.2 Discrete Output Camera Port Number Parameter

outputCameraPortNumber OBJECT-TYPE
SYNTAX	INTEGER (0..65535)
ACCESS	read-write
STATUS	mandatory
DESCRIPTION	
"<Definition> A value representing the number of physical camera port that is associated with the discrete output.  A value of zero (0) indicates that no camera port number is associated with the discrete output.  When read, this object returns the last value written.
<DescriptiveName> CctvSwitch.outputCameraPortNumber:identifier
<DataConceptType> Data Element"
::= {outputTableEntry 2}

--3.3.3.3 Discrete Output Monitor Port Number Parameter

outputMonitorPortNumber OBJECT-TYPE
SYNTAX	INTEGER (0..65535)
ACCESS	read-write
STATUS	mandatory
DESCRIPTION	
"<Definition> A value representing the number of physical monitor port associated with the discrete output.  A value of zero (0) indicates that no monitor port number is associated with the output.  When read, this object returns the last value written.
<DescriptiveName> CctvSwitch.outputMonitorPortNumber:identifier
<DataConceptType> Data Element"
::= {outputTableEntry 3}

--3.3.3.4 Discrete Output Label Number Parameter

outputLabelNumber OBJECT-TYPE
SYNTAX	INTEGER (0..65535)
ACCESS	read-write
STATUS	mandatory
DESCRIPTION	
"<Definition> A value representing the label number from the switch label table that is associated with this discrete output for this monitor port.  Writing a value to this object changes the label assignment.  When read, this object returns last value written.  A value of zero (0) indicates that no output label is displayed.  
<DescriptiveName> CctvSwitch.outputLabelNumber:identifier
<DataConceptType> Data Element"
::= {outputTableEntry 4}


--3.4 CCTV SWITCH LABEL OBJECTS
cctvSwitchLabel	OBJECT IDENTIFIER ::= { cctvSwitch 3 }

--3.4.1 Maximum Number of Labels Parameter

labelMaximum OBJECT-TYPE
SYNTAX	INTEGER (1..65535)
ACCESS	read-only
STATUS	mandatory
DESCRIPTION	
"<Definition> Defines the maximum number of labels in the label table.  A label is defined as text with position, font, and color information. 
<DescriptiveName> CctvSwitch.labelMaximum:quantity
<DataConceptType> Data Element 
<Unit> labels"
::= {cctvSwitchLabel 1}

--3.4.2 Switch Label Table

labelSwitchTable OBJECT-TYPE
SYNTAX	SEQUENCE OF LabelSwitchEntry
ACCESS	not-accessible
STATUS	mandatory
DESCRIPTION 
"<Definition> This table contains data specific to each label.  A label is defined as text with position, font, and color information. Each row in the table identifies a single label.  Table rows are set by the manufacturer, and row creation/deletion is not supported.
<DescriptiveName> CctvSwitch.labelSwitchTable
<DataConceptType> Entity Type
<TableType> static "
::= {cctvSwitchLabel 2}

labelSwitchEntry OBJECT-TYPE
SYNTAX	LabelSwitchEntry
ACCESS	not-accessible
STATUS	mandatory
DESCRIPTION 
"<Definition> Parameters of the label table.
<DescriptiveName> CctvSwitch.labelSwitchEntry
<DataConceptType> Entity Type "
INDEX {labelNumber} 
::= {labelSwitchTable 1}

LabelSwitchEntry ::= SEQUENCE {
	labelNumber			INTEGER,
        labelText			OCTET STRING,
        labelFontNumber		INTEGER,
        labelHeight			INTEGER,
        labelColor			INTEGER,
	labelStartRow			INTEGER,
	labelStartColumn		INTEGER,
	labelActive			OCTET STRING
	}

--3.4.2.1 Label Number Parameter

labelNumber OBJECT-TYPE
SYNTAX	INTEGER (1..65535)
ACCESS	read-only
STATUS	mandatory
DESCRIPTION 
"<Definition>The number associated with each individual label.
<DescriptiveName> CctvSwitch.labelNumber:identifier
<DataConceptType> Data Element"
::= { labelSwitchEntry 1}

--3.4.2.2 Text Label String Parameter

labelText OBJECT-TYPE
SYNTAX	OCTET STRING (SIZE(0..255))
ACCESS	read-write
STATUS	mandatory
DESCRIPTION 
"<Definition> Text for the label.  The label text must fit within the frame-size available for the application.
<DescriptiveName> CctvSwitch.labelText:text
<DataConceptType> Data Element"
::= { labelSwitchEntry 2}

--3.4.2.3 Label Font Number Parameter

labelFontNumber OBJECT-TYPE
SYNTAX	INTEGER (1..255)
ACCESS	read-write
STATUS	mandatory
DESCRIPTION 
"<Definition> Designates the font number to be displayed.  Only one font style may be supported and that font style is taken to be the default style.  When read, this object returns last value written.
        Value		Meaning
        1		other,
2 designates the default ASCII encoded text characters [0-9, A-Z , colon (:), period (.), slash (/), apostrophe (‘) and space ( )] to be displayed,
3..255		reserved.
<DescriptiveName> CctvSwitch.labelFontNumber:code
<DataConceptType> Data Element"
DEFVAL { 2 }
::= { labelSwitchEntry 3}

--3.4.2.4 Label Height Parameter

labelHeight OBJECT-TYPE
SYNTAX	INTEGER (0..255)
ACCESS	read-write
STATUS	mandatory
DESCRIPTION 
"<Definition> Height of this label text represented as a percent of screen filled by the text and scaled to a range of zero (0) and 255 to fit height of screen.  A height of zero (0) indicates that a label is not displayed and a height of 255 indicates that the label is presented at a maximum height.  When read, this object returns last value written.
<DescriptiveName> CctvSwitch.labelHeight:quantity
<DataConceptType> Data Element
<Unit> scalar 0 to 255"
::= { labelSwitchEntry 4}

--3.4.2.5 Label Color Parameter

labelColor OBJECT-TYPE
SYNTAX	INTEGER {
        blue(1),
        green(2),
        cyan(3),
        red(4),
        magenta(5),
        brown(6),
        white(7),
        grey(8),
        lightBlue(9),
        lightGreen(10),
        lightCyan(11),
        lightRed(12),
        lightMagenta(13),
        yellow(14),
        brightWhite(15),
        black(16)}
ACCESS	read-write
STATUS	mandatory
DESCRIPTION 
"<Definition> Color of the label characters.  The default color must always be supported.  The color is defined as follows:
        Value		Meaning
        1		blue,
        2		green,
        3		cyan,
        4		red,
        5		magenta,
        6		brown,
        7		white,
        8		grey,
        9		lightBlue,
        10		lightGreen,
        11		lightCyan,
        12		lightRed,
        13		lightMagenta,
        14		yellow,
15		brightWhite,
16 black.
When read, this object returns last value written.
<DescriptiveName> CctvSwitch.labelColor:code
<DataConceptType> Data Element"
DEFVAL { white }
::= { labelSwitchEntry 5}

--3.4.2.6 Label Start Row Parameter

labelStartRow OBJECT-TYPE
SYNTAX	INTEGER (0..255)
ACCESS	read-write
STATUS	mandatory
DESCRIPTION 
"<Definition> Start of text row number representing the vertical position on the screen where the text is to be displayed and scaled to a range of zero (0) to 255.  Zero (0) – zero (0) is designated as the upper left corner of the display.  When read, this object returns last value written.
<DescriptiveName> CctvSwitch.labelStartRow:identifier
<DataConceptType> Data Element"
::= { labelSwitchEntry 6}

--3.4.2.7 Label Start Column Parameter

labelStartColumn OBJECT-TYPE
SYNTAX	INTEGER (0..255)
ACCESS	read-write
STATUS	mandatory
DESCRIPTION 
"<Definition> Start of text column number representing the horizontal position on the screen where the text is to be displayed and scaled to a range of zero (0) to 255.  Zero (0) – zero (0) is designated as the upper left corner of the display.  When read, this object returns last value written.
<DescriptiveName> CctvSwitch.labelStartColumn:identifier
<DataConceptType> Data Element"
::= { labelSwitchEntry 7}

--3.4.2.8 Label Active Control Parameter

labelActive OBJECT-TYPE
SYNTAX	OCTET STRING (SIZE(1))
ACCESS	read-write
STATUS	mandatory
DESCRIPTION 
"<Definition> The object denotes whether or not the label is enabled for display.  
        Bit 7		0 = DISABLED, 1 = ENABLED for display of the label (MSB),	  
        Bits6..0 	Reserved (Bit0 = LSB).
<DescriptiveName> CctvSwitch.labelActive:text
<DataConceptType> Data Element"
::= { labelSwitchEntry 8}


--3.5 CCTV SWITCH TIME DATE OVERLAY OBJECTS

switchTimeDateOverlay	OBJECT IDENTIFIER ::= { cctvSwitch 4 }

--3.5.1 Assignment Time Format Parameter

timeFormat OBJECT-TYPE
SYNTAX	INTEGER {
        other(1),
        noTime(2),
        timeType1(3),
        timeType2(4)}
ACCESS	read-write
STATUS	mandatory
DESCRIPTION	
"<Definition> A value representing the display format for time, as described below:
        Value		Meaning
1 other time format,
2 no time function is supported by this device,
3 time is displayed in 12 hour format (HH:MM:SS pm),
4 time is displayed in 24 hour format (HH:MM:SS).
<DescriptiveName> CctvSwitch.cctvSwitchAssignmentTimeFormat:code
<DataConceptType> Data Element"
::= { switchTimeDateOverlay 1}

--3.5.2 Assignment Date Format Parameter

dateFormat OBJECT-TYPE
SYNTAX	INTEGER {
        other(1),
        noDate(2),
        dateType1(3),
        dateType2(4),
        dateType3(5),
        dateType4(6),
        dateType5(7),
        dateType6(8)}
ACCESS	read-write
STATUS	mandatory
DESCRIPTION	
"<Definition> A value representing the display format for time, as described below:
        Value		Meaning
1 other date format,
2 no date function is supported by this device,
3 date is displayed as (MM/DD/YYYY) with month being a numeric designation,
4 date is displayed (YYYY/MM/DD) with month being a numeric designation,
5 date is displayed (Month/DD/YYYY) with month being a 3-letter abbreviation of the month,
6 date is displayed as (MM/DD/YYYY) with month being a numeric designation,
7 date is displayed (YYYY/MM/DD) with month being a numeric designation,
8 date is displayed (Month/DD/YYYY) with month being a 3-letter abbreviation of the month.
<DescriptiveName> CctvSwitch.cctvSwitch AssignmentDateFormat:code
<DataConceptType> Data Element"
::= { switchTimeDateOverlay 2}

--3.5.3 Time Date Overlay Font Number Parameter

timeDateOverlayFontNumber OBJECT-TYPE
SYNTAX INTEGER {
        other(1),
        ascii(2)}
ACCESS read-write
STATUS mandatory
DESCRIPTION
"<Definition> Designates the time date overlay font number to be displayed. Only one font style may be supported and that font style
is taken to be the default style.  When read, this object returns last value written.
     Value              Meaning
       1                other
       2                designates the default ASCII encoded text characters [0-9, A-Z, colon(:), period(.), slash(/), apostrophe(') and space( ) to be
                        diplayed
<DescriptiveName> CctvSwitch.timeDateOverlayFontNumber:code
<DataConceptType> Data Element"
DEFVAL { ascii }
::={switchTimeDateOverlay 3}

--3.5.4 Time Date Overlay Height Parameter

timeDateOverlayHeight OBJECT-TYPE
SYNTAX	INTEGER (0..255)
ACCESS	read-write
STATUS	mandatory
DESCRIPTION 
"<Definition> Height of the time date overlay text represented as a percent of screen filled by the text and scaled to a range of zero (0) and 255 to fit height of screen.  A height of zero (0) indicates that a time date overlay is not displayed and a height of 255 indicates that the time date overlay is presented at a maximum height.  When read, this object returns last value written.
<DescriptiveName> CctvSwitch.timeDateOverlayHeight:quantity
<DataConceptType> Data Element
<Unit> scalar 0 to 255"
::= { switchTimeDateOverlay 4}

--3.5.5 Time Date Overlay Color Parameter

timeDateOverlayColor OBJECT-TYPE
SYNTAX	INTEGER {
        blue(1),
        green(2),
        cyan(3),
        red(4),
        magenta(5),
        brown(6),
        white(7),
        grey(8),
        lightBlue(9),
        lightGreen(10),
        lightCyan(11),
        lightRed(12),
        lightMagenta(13),
        yellow(14),
        brightWhite(15),
        black(16)}
ACCESS	read-write
STATUS	mandatory
DESCRIPTION 
"<Definition> Color of the time date overlay characters.  The default color must always be supported.  The color is defined as follows:
        Value		Meaning
        1		blue,
        2		green,
        3		cyan,
        4		red,
        5		magenta,
        6		brown,
        7		white,
        8		grey,
        9		lightBlue,
        10		lightGreen,
        11		lightCyan,
        12		lightRed,
        13		lightMagenta,
        14		yellow,
15		brightWhite,
17 black.
When read, this object returns last value written.
<DescriptiveName> CctvSwitch.timeDateOverlayColor:code
<DataConceptType> Data Element"
DEFVAL { white }
::= { switchTimeDateOverlay 5}

--3.5.6 Time Date Overlay Start Row Parameter

timeDateOverlayStartRow OBJECT-TYPE
SYNTAX	INTEGER (0..255)
ACCESS	read-write
STATUS	mandatory
DESCRIPTION 
"<Definition> Start of text row number representing the vertical position on the screen where the time date overlay text is to be displayed and scaled to a range of zero (0) to 255.  Zero (0) – zero (0) is designated as the upper left corner of the display.  When read, this object returns last value written.
<DescriptiveName> CctvSwitch.timeDateOveralyStartRow:identifier
<DataConceptType> Data Element"
::= { switchTimeDateOverlay 6}

--3.5.7 Time Date Overlay Start Column Parameter

timeDateOverlayStartColumn OBJECT-TYPE
SYNTAX	INTEGER (0..255)
ACCESS	read-write
STATUS	mandatory
DESCRIPTION 
"<Definition> Start of text column number representing the horizontal position on the screen where the time date overlay text is to be displayed and scaled to a range of zero (0) to 255.  Zero (0) – zero (0) is designated as the upper left corner of the display.  When read, this object returns last value written.
<DescriptiveName> CctvSwitch.timeDateOverlayStartColumn:identifier
<DataConceptType> Data Element"
::= { switchTimeDateOverlay 7}


--3.6 CCTV SWITCH ASSIGNMENT OBJECTS

cctvSwitchAssignment	OBJECT IDENTIFIER ::= { cctvSwitch 5 }

--3.6.1 Maximum Number of Assignable Camera Ports Parameter

cctvSwitchAssignmentMaximumCameraPorts OBJECT-TYPE
SYNTAX	INTEGER (1..65535)
ACCESS	read-only
STATUS	mandatory
DESCRIPTION	
"<Definition> A value representing the maximum number of physical camera ports.
<DescriptiveName> CctvSwitch.cctvSwitchAssignmentMaximumCameraPorts:quantity
<DataConceptType> Data Element
<Unit> camera ports"
::= {cctvSwitchAssignment 1}

--3.6.2 Maximum Number of Assignable Monitor Ports Parameter

cctvSwitchAssignmentMaximumMonitorPorts OBJECT-TYPE
SYNTAX	INTEGER (1..65535)
ACCESS	read-only
STATUS	mandatory
DESCRIPTION	
"<Definition> A value representing the maximum number of physical monitor ports.
<DescriptiveName> CctvSwitch.cctvSwitchAssignmentMaximumMonitorPorts:quantity
<DataConceptType> Data Element
<Unit> monitor ports"
::= {cctvSwitchAssignment 2}

--3.6.3 Switch Assignment Table

cctvSwitchAssignmentTable  OBJECT-TYPE
SYNTAX	SEQUENCE OF CctvSwitchAssignmentTableEntry
ACCESS	not-accessible
STATUS	mandatory
DESCRIPTION 
"<Definition> A table containing data specific to the CCTV switch assignments, text overlays and assignment status.  Table rows are set by the manufacturer, and row creation/deletion is not supported.
<DescriptiveName> CctvSwitch.cctvSwitchAssignmentTable
<DataConceptType> Entity Type
<TableType> static"
::= {cctvSwitchAssignment 3}

cctvSwitchAssignmentTableEntry OBJECT-TYPE
SYNTAX	CctvSwitchAssignmentTableEntry
ACCESS	not-accessible
STATUS	mandatory
DESCRIPTION 
"<Definition> Parameters within the CCTV switch table that address switch assignments and format of the time and date stamp.
<DescriptiveName> CctvSwitch.cctvSwitchAssignmentTableEntry
<DataConceptType> Entity Type"
INDEX {cctvSwitchAssignmentMonitorPortNumber} 
::= {cctvSwitchAssignmentTable 1}

CctvSwitchAssignmentTableEntry ::= SEQUENCE {
	cctvSwitchAssignmentMonitorPortNumber		INTEGER,
	cctvSwitchAssignmentMonitorPortLabelNumber		INTEGER,
        cctvSwitchAssignmentMonitorMode			INTEGER,
        cctvSwitchAssignmentCameraPortNumber		INTEGER,
	cctvSwitchAssignmentCameraPortLabelNumber		INTEGER,
        cctvSwitchAssignmentTimeDateOverlay			INTEGER,
        cctvSwitchAssignmentSequenceNumber		INTEGER,
        cctvSwitchAssignmentStatus				INTEGER,
        cctvSwitchAssignmentGroupStatus			INTEGER,
	cctvSwitchAssignmentGroupSequenceStatus		INTEGER
        }

--3.6.3.1 Assignment Monitor Port Number Parameter

cctvSwitchAssignmentMonitorPortNumber OBJECT-TYPE
SYNTAX	INTEGER (1..65535)
ACCESS	read-only
STATUS	mandatory
DESCRIPTION	
"<Definition> A value representing the number of physical monitor port.
<DescriptiveName> CctvSwitch.cctvSwitchAssignmentMonitorPortNumber:identifier
<DataConceptType> Data Element"
::= {cctvSwitchAssignmentTableEntry 1}

--3.6.3.2 Assignment Monitor Label Number Parameter

cctvSwitchAssignmentMonitorPortLabelNumber OBJECT-TYPE
SYNTAX	INTEGER (0..65535)
ACCESS	read-write
STATUS	mandatory
DESCRIPTION	
"<Definition> A value representing the label number from the switch label table that is associated with this monitor port.  When read, this object returns last value written.
<DescriptiveName> CctvSwitch.cctvSwitchMonitorPortLabelNumber:identifier
<DataConceptType> Data Element"
::= {cctvSwitchAssignmentTableEntry 2}

--3.6.3.3 Assignment Monitor Mode Parameter

cctvSwitchAssignmentMonitorMode OBJECT-TYPE
SYNTAX	INTEGER {
				other(1),
				displayCamera(2),
				displaySequence(3),
				holdSequence(4),
				nextSequentialCamera(5),
				previousSequentialCamera(6),
				restartSequence(7)}
ACCESS	read-write
STATUS	mandatory
DESCRIPTION	
"<Definition> An assignment command, as follows:
        Value		Meaning
        1		other monitor mode command,
2	display the camera port identified by the cctvSwitchAssignmentCameraPortNumber on this monitor port,
3	display the sequence identified by the cctvSwitchAssignmentSequenceNumber on this monitor port,
        4		hold the sequence,
        5		hold the sequence and then go to the next sequential camera in the sequence,
6	hold the sequence and then go to the previous sequential camera in the sequence,
7 restart the currently displayed sequence.
When read, this object returns last value written.
<DescriptiveName> CctvSwitch.cctvSwitchAssignmentMonitorMode:code
<DataConceptType> Data Element"
::= {cctvSwitchAssignmentTableEntry 3}

--3.6.3.4 Assignment Camera Port Number Parameter

cctvSwitchAssignmentCameraPortNumber OBJECT-TYPE
SYNTAX	INTEGER (1..65535)
ACCESS	read-write
STATUS	mandatory
DESCRIPTION	
"<Definition> A value representing the number of physical camera port to be displayed on the monitor port.  When read, this object returns last value written.
<DescriptiveName> CctvSwitch.cctvSwitchAssignmentCameraPortNumber:identifier
<DataConceptType> Data Element"
::= {cctvSwitchAssignmentTableEntry 4}

--3.6.3.5 Assignment Camera Label Number Parameter

cctvSwitchAssignmentCameraPortLabelNumber OBJECT-TYPE
SYNTAX	INTEGER (0..65535)
ACCESS	read-write
STATUS	mandatory
DESCRIPTION	
"<Definition> A value representing the label number from the switch label table that is associated with the camera port assignment.  A value of zero (0) indicates that there is no label associated with this camera port assignment.  When read, this object returns last value written.
<DescriptiveName> CctvSwitch.cctvSwitchCameraPortLabelNumber:identifier
<DataConceptType> Data Element"
::= {cctvSwitchAssignmentTableEntry 5}

--3.6.3.6 Assignment Time Date Overlay Parameter

cctvSwitchAssignmentTimeDateOverlay OBJECT-TYPE
SYNTAX	INTEGER {
				other(1),
        timeNotDisplayed(2),
				timeDisplayed(3),
				dateDisplayed(4),
				bothTimeDateDisplayed(5)}
ACCESS	read-write
STATUS	mandatory
DESCRIPTION	
"<Definition> A value representing the state of the time display for this monitor port, as defined below:
        Value		Meaning
        1		other time date overlay command on this monitor port,
        2		time overlay is not displayed on this monitor port,
        3		time overlay is displayed on this monitor port,
        4		date overlay is displayed on this monitor port,
        5		both time and date overlays are displayed on this monitor port.
When read, this object returns last value written.
<DescriptiveName> CctvSwitch.cctvSwitchAssignmentTimeDateOverlay:code
<DataConceptType> Data Element"
::= {cctvSwitchAssignmentTableEntry 6}

--3.6.3.7 Assignment Sequence Number Parameter

cctvSwitchAssignmentSequenceNumber OBJECT-TYPE
SYNTAX	INTEGER (1..65535)
ACCESS	read-write
STATUS	mandatory
DESCRIPTION	
"<Definition> A value representing the number of the sequence to be displayed on the monitor port.
<DescriptiveName> CctvSwitch.cctvSwitchAssignmentSequenceNumber:identifier
<DataConceptType> Data Element"
::= {cctvSwitchAssignmentTableEntry 7}

--3.6.3.8 Assignment Status Parameter

cctvSwitchAssignmentStatus OBJECT-TYPE
SYNTAX	INTEGER {
				other(1),
				noCameraPortAssignment(2),				
        cameraPortOutOfRange(3),
				monitorPortOutOfRange(4),
				dwellTimeOutOfRange(5),
				noSequenceDefined(6)}
ACCESS	read-only
STATUS	mandatory
DESCRIPTION
"<Definition> A value representing the camera to monitor and sequence assignment status, as described below:
	Value		Meaning
1 other assignment status,
2 no camera port assigned to this monitor,
3 camera port number is out of range,
4 monitor port number is out of range,
5 dwell time is out of range,
6 no sequence is defined for this assignment.
<DescriptiveName> CctvSwitch.cctvSwitchAssignmentStatus:code
<DataConceptType> Data Element"
DEFVAL { noCameraPortAssignment }
::={cctvSwitchAssignmentTableEntry 8}

--3.6.3.9 Assignment Group Status Parameter

cctvSwitchAssignmentGroupStatus OBJECT-TYPE
SYNTAX	INTEGER {
				other(1),
				groupAssignmentFailed(2),
				groupUnidentified(3)}
ACCESS	read-only
STATUS	mandatory
DESCRIPTION	
"<Definition> Status of the group assignment, as follows:
        Value		Meaning
        1		other group status,
2	the group assignment failed on this monitor port,
3 no group is identified for this monitor port.
<DescriptiveName> CctvSwitch.cctvSwitchAssignmentGroupStatus:code
<DataConceptType> Data Element"
::= {cctvSwitchAssignmentTableEntry 9}

--3.6.3.10 Assignment Group Status Parameter

cctvSwitchAssignmentGroupSequenceStatus OBJECT-TYPE
SYNTAX	INTEGER {
				other(1),
				groupSequenceAssignmentFailed(2),
				groupSequenceUnidentified(3)}
ACCESS	read-only
STATUS	mandatory
DESCRIPTION	
"<Definition> Status of the sequence of groups assignment, as follows:
        Value		Meaning
        1		other group sequence status,
2 the sequence of groups assignment failed on this monitor port,
3 no sequence of groups is identified for this monitor port.
<DescriptiveName> CctvSwitch.cctvSwitchAssignmentGroupSequenceStatus:code
<DataConceptType> Data Element"
::= {cctvSwitchAssignmentTableEntry 10}

--3.6.4 Global Label Disable Parameter

cctvSwitchGlobalLabelDisable OBJECT-TYPE
SYNTAX	OCTET STRING (SIZE(1))
ACCESS	read-only
STATUS	mandatory
DESCRIPTION 
"<Definition> The object turns off all labels on the CCTV switch, but does not turn off the time and date overlays.  A value of 0 denotes that labels are active.  A value of 1 denotes that all labels, except for the time and date overlays are globally disabled on the CCTV switch and not displayed.  
        Bit 7		0 =  ENABLED, 1 = DISABLED for the global display of labels (MSB),	  
        Bits6..0 	Reserved (Bit0 = LSB).
<DescriptiveName> CctvSwitch.cctvSwitchGlobalLabelDisable:text
<DataConceptType> Data Element"
::= {cctvSwitchAssignment 4}


--3.7 CCTV SWITCH SEQUENCE OBJECTS

cctvSwitchSequence	OBJECT IDENTIFIER ::= { cctvSwitch 6 }


--3.7.1 Maximum Number of Sequences Parameter

cctvSwitchMaximumSequences OBJECT-TYPE
SYNTAX	INTEGER (1..65535)
ACCESS	read-only
STATUS	mandatory
DESCRIPTION	
"<Definition> A value representing the maximum number of allowable sequences.
<DescriptiveName> CctvSwitch.cctvSwitchMaximumSequences:quantity
<DataConceptType> Data Element
<Unit> sequences"
::= {cctvSwitchSequence 1}

--3.7.2 Sequence Table

cctvSwitchSequenceTable OBJECT-TYPE
SYNTAX	SEQUENCE OF CctvSwitchSequenceTableEntry
ACCESS	not-accessible
STATUS	mandatory
DESCRIPTION 
"<Definition> A table containing data specific to the CCTV switch sequence definition.  Table rows are set by the manufacturer, and row creation/deletion is not supported.
<DescriptiveName> CctvSwitch.cctvSwitchSequenceTable
<DataConceptType> Entity Type
<TableType> static"
::= {cctvSwitchSequence 3}

cctvSwitchSequenceTableEntry OBJECT-TYPE
SYNTAX	CctvSwitchSequenceTableEntry
ACCESS	not-accessible
STATUS	mandatory
DESCRIPTION 
"<Definition> Parameters within the CCTV sequence table that address the definition and labeling of a sequence.
<DescriptiveName> CctvSwitch.cctvSwitchSequenceTableEntry
<DataConceptType> Entity Type"
INDEX {cctvSwitchSequenceNumber} 
::= {cctvSwitchSequenceTable 1}

CctvSwitchSequenceTableEntry ::= SEQUENCE {
	cctvSwitchSequenceNumber				INTEGER,
	cctvSwitchSequenceDefinition				OCTET STRING,
        cctvSwitchSequenceLabelNumber			INTEGER
        }

--3.7.2.1 Sequence Number Parameter

cctvSwitchSequenceNumber OBJECT-TYPE
SYNTAX	INTEGER (1..65535)
ACCESS	read-only
STATUS	mandatory
DESCRIPTION	
"<Definition> The number used as an identifier for each individual sequence.
<DescriptiveName> CctvSwitch.cctvSwitchSequenceNumber:identifier
<DataConceptType> Data Element"
::= {cctvSwitchSequenceTableEntry 1}

--3.7.2.2 Sequence Definition Parameter

cctvSwitchSequenceDefinition OBJECT-TYPE
SYNTAX	OCTET STRING (SIZE(3..255))
ACCESS	read-write
STATUS	mandatory
DESCRIPTION	
"<Definition> A string defining the camera ports, and dwell times, for the sequence to be displayed on the specified monitor port, as described below:
	Bytes1,2	camera port number associated with the monitor port displayed in the sequence,
	Byte3		dwell time in seconds for the camera port displayed in the sequence.
 A sequence can support up to 85 camera port displays on a single monitor port.
<DescriptiveName> CctvSwitch.cctvSwitchSequenceDefinition:text
<DataConceptType> Data Element"
::= {cctvSwitchSequenceTableEntry 2}

--3.7.2.3 Sequence Label Number Parameter

cctvSwitchSequenceLabelNumber OBJECT-TYPE
SYNTAX	INTEGER (0..65535)
ACCESS	read-write
STATUS	mandatory
DESCRIPTION	
"<Definition> A value representing the label number from the switch label table that is associated with this sequence.  A value of zero (0) indicates that there is no label associated with this sequence.  When read, this object returns last value written.
<DescriptiveName> CctvSwitch.cctvSwitchSequenceLabelNumber:identifier
<DataConceptType> Data Element"
::= {cctvSwitchSequenceTableEntry 3}


--3.8 CCTV SWITCH GROUP OBJECTS

cctvSwitchGroup	OBJECT IDENTIFIER ::= { cctvSwitch 7 }

--3.8.1 Maximum Number of Groups Parameter

cctvSwitchMaximumGroups OBJECT-TYPE
SYNTAX	INTEGER (1..65535)
ACCESS	read-only
STATUS	mandatory
DESCRIPTION	
"<Definition> A value representing the maximum number of allowable groups.
<DescriptiveName> CctvSwitch.cctvSwitchMaximumGroups:quantity
<DataConceptType> Data Element
<Unit> groups"
::= {cctvSwitchGroup 1}

--3.8.2 Group Table

cctvSwitchGroupTable OBJECT-TYPE
SYNTAX	SEQUENCE OF CctvSwitchGroupTableEntry
ACCESS	not-accessible
STATUS	mandatory
DESCRIPTION 
"<Definition> A table containing data specific to the CCTV switch group definition.  Table rows are set by the manufacturer, and row creation/deletion is not supported.
<DescriptiveName> CctvSwitch.cctvSwitchGroupTable
<DataConceptType> Entity Type
<TableType> static"
::= {cctvSwitchGroup 2}

cctvSwitchGroupTableEntry OBJECT-TYPE
SYNTAX	CctvSwitchGroupTableEntry
ACCESS	not-accessible
STATUS	mandatory
DESCRIPTION 
"<Definition> Parameters within the CCTV group table that address the definition and labeling of a group.
<DescriptiveName> CctvSwitch.cctvSwitchGroupTableEntry
<DataConceptType> Entity Type"
INDEX {cctvSwitchGroupNumber} 
::= {cctvSwitchGroupTable 1}

CctvSwitchGroupTableEntry ::= SEQUENCE {
	cctvSwitchGroupNumber				INTEGER,
	cctvSwitchGroupDefinition				OCTET STRING,
        cctvSwitchGroupLabelNumber				INTEGER
        }

--3.8.2.1 Group Number Parameter

cctvSwitchGroupNumber OBJECT-TYPE
SYNTAX	INTEGER (1..65535)
ACCESS	read-only
STATUS	mandatory
DESCRIPTION	
"<Definition> The number used as an identifier for each individual group.
<DescriptiveName> CctvSwitch.cctvSwitchGroupNumber:identifier
<DataConceptType> Data Element"
::= {cctvSwitchGroupTableEntry 1}

--3.8.2.2 Group Definition Parameter

cctvSwitchGroupDefinition OBJECT-TYPE
SYNTAX	OCTET STRING (SIZE(4..255))
ACCESS	read-write
STATUS	mandatory
DESCRIPTION	
"<Definition> A string defining the camera ports, and monitor ports, for the group to be displayed, as described below:
	Bytes1,2	camera port number associated with the monitor port displayed in the group,
Bytes3,4	monitor port number on which the associated camera port is displayed in the group.
 A group can support up to 63 camera port displays on their associated monitor ports.
<DescriptiveName> CctvSwitch.cctvSwitchGroupDefinition:text
<DataConceptType> Data Element"
::= {cctvSwitchGroupTableEntry 2}

--3.8.2.3 Group Label Number Parameter

cctvSwitchGroupLabelNumber OBJECT-TYPE
SYNTAX	INTEGER (0..65535)
ACCESS	read-write
STATUS	mandatory
DESCRIPTION	
"<Definition> A value representing the label number from the switch label table that is associated with this group.  A value of zero (0) indicates that there is no label associated with this group.  When read, this object returns last value written.
<DescriptiveName> CctvSwitch.cctvSwitchGroupLabelNumber:identifier
<DataConceptType> Data Element"
::= {cctvSwitchGroupTableEntry 3}

--3.8.3 Activate Group Parameter

cctvSwitchActivateGroup OBJECT-TYPE
SYNTAX	INTEGER (0..255)
ACCESS	read-write
STATUS	mandatory
DESCRIPTION
"<Definition> A command to display the group identified by this parameter.  A value of 0 means that no group is displayed.  When read, this object returns last value written.
<DescriptiveName> CctvSwitch.cctvSwitchGoToGroup:identifier
<DataConceptType> Data Element"
DEFVAL { 0 }
::={cctvSwitchGroup 3}


--3.9 CCTV SWITCH GROUP SEQUENCE OBJECTS

cctvSwitchGroupSequence	OBJECT IDENTIFIER ::= { cctvSwitch 8 }

--3.9.1 Maximum Number of Group Sequences Parameter

cctvSwitchMaximumGroupSequences OBJECT-TYPE
SYNTAX	INTEGER (1..65535)
ACCESS	read-only
STATUS	mandatory
DESCRIPTION	
"<Definition> A value representing the maximum number of allowable sequences of groups.
<DescriptiveName> CctvSwitch.cctvSwitchMaximumGroupSequences:quantity
<DataConceptType> Data Element
<Unit> sequences of groups"
::= {cctvSwitchGroupSequence 1}

--3.9.2 Group Sequence Table

cctvSwitchGroupSequenceTable OBJECT-TYPE
SYNTAX	SEQUENCE OF CctvSwitchGroupSequenceTableEntry
ACCESS	not-accessible
STATUS	mandatory
DESCRIPTION 
"<Definition> A table containing data specific to the CCTV switch sequence of groups definition.  Table rows are set by the manufacturer, and row creation/deletion is not supported.
<DescriptiveName> CctvSwitch.cctvSwitchGroupSequenceTable
<DataConceptType> Entity Type
<TableType> static"
::= {cctvSwitchGroupSequence 2}

cctvSwitchGroupSequenceTableEntry OBJECT-TYPE
SYNTAX	CctvSwitchGroupSequenceTableEntry
ACCESS	not-accessible
STATUS	mandatory
DESCRIPTION 
"<Definition> Parameters within the CCTV group sequence table that address the definition and labeling of a sequence of groups.
<DescriptiveName> CctvSwitch.cctvSwitchGroupSequenceTableEntry
<DataConceptType> Entity Type"
INDEX {cctvSwitchGroupSequenceNumber} 
::= {cctvSwitchGroupSequenceTable 1}

CctvSwitchGroupSequenceTableEntry ::= SEQUENCE {
	cctvSwitchGroupSequenceNumber			INTEGER,
	cctvSwitchGroupSequenceDefinition			OCTET STRING,
        cctvSwitchGroupSequenceLabelNumber		INTEGER
        }

--3.9.2.1 Group Number Parameter

cctvSwitchGroupSequenceNumber OBJECT-TYPE
SYNTAX	INTEGER (1..65535)
ACCESS	read-only
STATUS	mandatory
DESCRIPTION	
"<Definition> The number used as an identifier for each individual sequence of groups.
<DescriptiveName> CctvSwitch.cctvSwitchGroupSequenceNumber:identifier
<DataConceptType> Data Element"
::= {cctvSwitchGroupSequenceTableEntry 1}

--3.9.2.2 Group Sequence Definition Parameter

cctvSwitchGroupSequenceDefinition OBJECT-TYPE
SYNTAX	OCTET STRING (SIZE(5..255))
ACCESS	read-write
STATUS	mandatory
DESCRIPTION	
"<Definition> A string defining the group number and dwell times for the sequence of groups to be displayed, as described below:
Bytes1,2	group number parameter from the group table that identifies the individual group to be displayed,
Byte3	dwell time in seconds for the group displayed in the sequence of groups.
 A group sequence can support up to 85 group displays.
<DescriptiveName> CctvSwitch.cctvSwitchGroupSequenceDefinition:text
<DataConceptType> Data Element"
::= {cctvSwitchGroupSequenceTableEntry 2}

--3.9.2.3 Group Sequence Label Number Parameter

cctvSwitchGroupSequenceLabelNumber OBJECT-TYPE
SYNTAX	INTEGER (0..65535)
ACCESS	read-write
STATUS	mandatory
DESCRIPTION	
"<Definition> A value representing the label number from the switch label table that is associated with this sequence of groups.  A value of zero (0) indicates that there is no label associated with this sequence of groups.  When read, this object returns last value written.
<DescriptiveName> CctvSwitch.cctvSwitchGroupSequenceLabelNumber:identifier
<DataConceptType> Data Element"
::= {cctvSwitchGroupSequenceTableEntry 3}

--3.9.3 Activate Group Sequence Parameter

cctvSwitchActivateGroupSequence OBJECT-TYPE
SYNTAX	INTEGER (0..255)
ACCESS	read-write
STATUS	mandatory
DESCRIPTION
"<Definition> A command to display the sequence of groups identified by this parameter.  A value of 0 means that no sequence of groups is displayed.  When read, this object returns last value written.
<DescriptiveName> CctvSwitch.cctvSwitchActivateGroupSequence:identifier
<DataConceptType> Data Element"
DEFVAL { 0 }
::={cctvSwitchGroupSequence 3}


--3.10 CCTV SWITCH CAMERA STATUS OBJECTS

cctvSwitchCameraStatus	OBJECT IDENTIFIER ::= { cctvSwitch 10 }

--3.10.1 Camera Status Table

cctvSwitchCameraStatusTable OBJECT-TYPE
SYNTAX	SEQUENCE OF CctvSwitchCameraStatusTableEntry
ACCESS	not-accessible
STATUS	mandatory
DESCRIPTION 
"<Definition> A table containing data specific to the camera status on CCTV camera ports.  Table rows are set by the manufacturer, and row creation/deletion is not supported.
<DescriptiveName> CctvSwitch.cctvSwitchCameraStatusTable
<DataConceptType> Entity Type
<TableType> static"
::= {cctvSwitchCameraStatus 1}

cctvSwitchCameraStatusTableEntry OBJECT-TYPE
SYNTAX	CctvSwitchCameraStatusTableEntry
ACCESS	not-accessible
STATUS	mandatory
DESCRIPTION 
"<Definition> Parameters within the CCTV camera status table that address the loss of video and label displayed upon video loss.
<DescriptiveName> CctvSwitch.cctvSwitchCameraStatusTableEntry
<DataConceptType> Entity Type"
INDEX {cctvSwitchCameraPortNumber} 
::= {cctvSwitchCameraStatusTable 1}

CctvSwitchCameraStatusTableEntry ::= SEQUENCE {
	cctvSwitchCameraPortNumber				INTEGER,
	cctvSwitchVideoLoss					OCTET STRING,
        cctvSwitchVideoLossLabelNumber			INTEGER
        }

--3.10.1.1 Camera Port Number Parameter

cctvSwitchCameraPortNumber OBJECT-TYPE
SYNTAX	INTEGER (1..65535)
ACCESS	read-only
STATUS	mandatory
DESCRIPTION	
"<Definition> A value representing the number of physical camera port.
<DescriptiveName> CctvSwitch.cctvSwitchCameraPortNumber:identifier
<DataConceptType> Data Element"
::= {cctvSwitchCameraStatusTableEntry 1}

--3.10.1.2 Video Loss Parameter

cctvSwitchVideoLoss OBJECT-TYPE
SYNTAX	OCTET STRING (SIZE(1))
ACCESS	read-only
STATUS	mandatory
DESCRIPTION 
"<Definition> The object denotes the presence or absence of video on this camera port.  
        Bit 7		0 = ABSENCE, 1 = PRESENCE of video picture signals (MSB),	  
        Bits6..0 	Reserved (Bit0 = LSB).
<DescriptiveName> CctvSwitch.cctvSwitchVideoLoss:text
<DataConceptType> Data Element"
::= {cctvSwitchCameraStatusTableEntry 2}

--3.10.1.3 Video Loss Label Number Parameter

cctvSwitchVideoLossLabelNumber OBJECT-TYPE
SYNTAX	INTEGER (0..65535)
ACCESS	read-write
STATUS	mandatory
DESCRIPTION	
"<Definition> A value representing the label number from the switch label table that is associated with the loss of video on this camera port.  A value of zero (0) indicates that there is no label associated with the loss of video on this camera port.  When read, this object returns last value written.
<DescriptiveName> CctvSwitch.cctvSwitchVideoLossLabelNumber:identifier
<DataConceptType> Data Element"
::= {cctvSwitchCameraStatusTableEntry 3}


END
