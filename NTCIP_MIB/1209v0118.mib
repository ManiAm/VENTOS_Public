-- Section 3 TSS MIB

--******************************************************************************
-- Filename:    1209v0118.mib
-- Source:      NTCIP 1209 TSS v01_18d dated 8/16/04
-- Description: This MIB defines those data elements that are expected to be used
--              by transportation sensor system devices.
-- MIB Revision History:
-- 09/27/04     Changed file from Word .Doc file
--              Changes status of objects to mandatory to
--              eliminate incompatible status errors
--              Restructured IMPORTS around NTCIP8004-A-2004 
--
--Copyright 1996 - 2004 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************

-- Section 3 
-- TSS MIB
-- This section defines those data elements that are expected to be used by transportation sensor system devices.  The data elements (objects) are -- described in terms of the ASN.1 (defined in ISO/IEC 8824-1, ISO/IEC 8824-2, ISO/IEC 8824-3, and ISO/IEC 8824-4) macro OBJECT-TYPE.  The 
-- OBJECT-TYPE macro is defined in RFC 1212.  The text provided from Clause 3.1 through the end of the section (except the clause headings) 
-- constitutes the NTCIP Standard TSS MIB.

-- The clauses below present the data elements in lexigraphical order of their OBJECT IDENTIFIERS that correspond to their physical location within -- the global naming tree.  The data elements defined in this document reside under the "tss" node of the global naming tree.  To aid in data 
-- element management, the "tss" node has been subdivided into logical categories, each defined by a node under the "tss" node.  The individual data -- elements are then located under the appropriate node.  

-- Nodes should not be confused with conformance groups, which are defined in Annex A.  A conformance group is a logical grouping of data elements -- that is used for conformance statements.  While conformance groups will frequently correspond to the nodal structure, a conformance group may 
-- contain data elements that are not lexigraphically ordered.  For example, a schedule conformance group may contain both "global" and "tss" 
-- specific data elements.

-- A data element status of Optional should not be confused with a conformance status of optional or mandatory as defined in Annex A.  The data 
-- element Status of Optional in the MIB means that the data element and data element definition is current.  The status of optional or mandatory in -- Annex A dictates whether the data element is required or not.

-- Text preceded by a double hyphen in the MIB definitions represent normative text for this standard.

-- All management applications shall reference the specific device MIB as provided by the device manufacturer for support and constraints 
-- (sub-ranges).


-- 3.1 TRANSPORTATION SENSOR SYSTEM (TSS) DATA ELEMENTS

TSS-MIB1 DEFINITIONS ::= BEGIN

-- the following OBJECT IDENTIFIERS are used in the TSS MIB:

IMPORTS
	OBJECT-TYPE
	FROM RFC-1212
	Counter
		FROM RFC1155-SMI
--	devices
--  	FROM TMIB-II;
	tss
        FROM NTCIP8004-A-2004;
-- For the purposes of this section, the following OBJECT IDENTIFIERS are used:
-- tss 	OBJECT IDENTIFIER ::= {devices 4}

-- 3.2 TSS SYSTEM SETUP DATA ELEMENTS
tssSystemSetup  OBJECT IDENTIFIER ::= { tss 1 }

--  This node contains the configuration data elements for traffic sensor systems

-- 3.2.1 Sensor System Reset Parameter

sensorSystemReset  OBJECT-TYPE
SYNTAX		INTEGER {	restart (1),
				reinitializeUserSettings (2),
				restoreFactoryDefaults (3),
				retune (4),
       				resyncSamplingPeriods (5),
       				shortDiagnostics (6),
       				fullDiagnostics (7) }
ACCESS	read-write
STATUS 	mandatory
DESCRIPTION	
"<Definition> This data element commands the entire sensor system to reset. The reset commands are described as follows:
	restart:   Restart command shall cause the unit to enter restart state and go through a complete shut-down and start-up process, causing a reset and initialization of the number of seconds since most recent device initialization to a value of zero;
	reinitalizeUserSettings:   Reinitialize User Settings command shall cause the unit to flush all volatile memory and reinitialize all settings to their user defined default values, and reset and initialize the number of seconds since most recent device initialization to a value of zero;
	restoreFactoryDefaults:   Restore Factory Defaults command shall cause the unit to flush all volatile memory, restore all settings to their factory default values, and reset and initialize the number of seconds since most recent device initialization to a value of zero;
	retune:   Retune command recalibrates unit background settings for all zones without resetting or flushing of any collected data;
	resyncSamplingPeriods:   Re-synchronize Sampling Periods command shall cause the unit to synchronize all startup sampling period clocks within 1 second of command issuance and a reset and initialize of the number of seconds since most recent device initialization to a value of zero;
	shortDiagnostics:   Short diagnostics command shall cause the unit to go through an abbreviated vendor specific diagnostic routine which may be the same as full diagnostics for some vendors;
	fullDiagnostics:   Full diagnostics shall cause the unit to go through a complete vendor specific diagnostic routine which may be the same as short diagnostics for some vendors, causing a reset and initialization of the number of seconds since most recent device initialization to a value of zero.
<DescriptiveName> Tss.sensorSystemReset:code
<DataConceptType> Data Element"
::= {tssSystemSetup 1 }

-- 3.2.2 Sensor System Status Parameter

sensorSystemStatus OBJECT-TYPE
SYNTAX 		INTEGER {	other (1),
       				oK (2),
				initializing (3) }
ACCESS  	read-only
STATUS   	mandatory
DESCRIPTION	
"<Definition> This data element provides an indication of the overall sensor system status, as follows:  
other:   Other indicates the presence of a hardware or software status that is not designated as either OK or initializing;
oK:   OK indicates that the unit is operating normally with no known hardware or software faults, with no implications about data;
initalizing:   Initializing indicates that the unit has encountered no fault, but is not ready for detection.
<DescriptiveName> Tss.sensorSystemStatus:code
<DataConceptType> Data Element"
::= { tssSystemSetup 2 }

-- 3.2.3 Sensor System Occupancy Type Parameter

sensorSystemOccupancyType OBJECT-TYPE
SYNTAX   	INTEGER {	normalizedOtherOccupancy (1),
       				nonNormalizedOccupancy (2),
      				zoneOccupancy (3),
       				normalizedSixFootLoopOccupancy (4),
       				normalizedTwoMeterLoopOccupancy (5) }
ACCESS  	read-only
STATUS   	mandatory
DESCRIPTION	
"<Definition> A set of flags on a per unit basis that indicate how to interpret the occupancy data parameter, as follows: 
normalizedOtherOccupancy:   Occupancy is normalized to other specific criteria that is not defined within this data element;
nonNormalizedOccupancy:   Occupancy is presented as non-normalized or raw occupancy data,
zoneOccupancy:   Occupancy is presented for a given zone,
normalizedSixFootLoopOccupancy:   Occupancy is normalized to a 6 foot by 6 foot loop,
normalizedTwoMeterLoopOccupancy:   Occupancy is normalized to a 2 meter by 2 meter loop.
<DescriptiveName> Tss. SensorSystemOccupancyType:code
<DataConceptType> Data Element "
::= { tssSystemSetup 3 }

-- 3.2.4 Maximum Number of Sensor Zones Parameter

maxSensorZones  OBJECT-TYPE
SYNTAX 		INTEGER (1..255)
ACCESS  	read-only
STATUS   	mandatory
DESCRIPTION	
"<Definition> The maximum number of sensor zones this transportation sensor system supports.  This data element indicates the maximum rows that shall appear in the sensorZoneTable data element.
<DescriptiveName> Tss.maxSensorZones:quantity
<DataConceptType> Data Element
<Unit> zone"
::= { tssSystemSetup 4 }

-- 3.2.5 Sensor Zone Table

sensorZoneTable  OBJECT-TYPE
SYNTAX  	SEQUENCE OF SensorZoneEntry
ACCESS 		not-accessible
STATUS  	mandatory
DESCRIPTION	
"<Definition> A table containing sensor zone unit parameters.  The number of rows in this table is equal to the maxSensorZones data element.  Table rows are set by the manufacturer, and row creation/deletion is not supported.
<DescriptiveName> Tss.sensorZoneTable
DataConceptType> Entity Type
<TableType> static "
::= { tssSystemSetup 5}

sensorZoneEntry  OBJECT-TYPE
SYNTAX  	SensorZoneEntry
ACCESS 		not-accessible
STATUS  	mandatory
DESCRIPTION	
"<Definition> Table for sensor zone parameters.
<DescriptiveName> sensorZoneEntry
<DataConceptType> Entity Type"
INDEX { sensorZoneNumber }
::= { sensorZoneTable 1 }

SensorZoneEntry ::= SEQUENCE {
	sensorZoneNumber		INTEGER,
	sensorZoneOptions		OCTET STRING,
	sensorZoneOptionsStatus		OCTET STRING,
	sensorZoneSamplePeriod		INTEGER,
	sensorZoneLabel			OCTET STRING,
	sensorZoneAndOperator		OCTET STRING,
	sensorZoneOrOperator		OCTET STRING
	}

-- 3.2.5.1 Sensor Zone Number Parameter

sensorZoneNumber  OBJECT-TYPE
SYNTAX   	INTEGER (1..255)
ACCESS  	read-only
STATUS   	mandatory
DESCRIPTION	
"<Definition> The numerical label or number of the sensor zone.  This value shall not exceed the maxSensorZones data element value.
<DescriptiveName> Tss.sensorZoneNumber:identifier
<DataConceptType> Data Element"
::= { sensorZoneEntry 1 }

-- 3.2.5.2 Sensor Zone Options Parameter

sensorZoneOptions  OBJECT-TYPE
SYNTAX   OCTET STRING (SIZE(1))
ACCESS  	read-write
STATUS   	mandatory 
DESCRIPTION	
"<Definition> A bit-mapped value as defined below for commanding this sensor zone to be ENABLED or DISABLED.  A non-configured system shall default to DISABLED.
bit 7	0 = DISABLED, 1 = ENABLED 	To command this sensor zone to be enabled or disabled;
bits 6..0		Reserved (bit 0 = LSB).
<DescriptiveName> Tss.sensorZoneOptions:text
<DataConceptType> Data Element"
::= { sensorZoneEntry 2 }

-- 3.2.5.3 Sensor Zone Options Status Parameter

sensorZoneOptionsStatus  OBJECT-TYPE
SYNTAX   	OCTET STRING (SIZE(1))
ACCESS  	read-only
STATUS   	mandatory
DESCRIPTION	
"<Definition> A bit-mapped value as defined below for indicating the status of whether this sensor zone is ENABLED or DISABLED.  
	bit 7		0 = DISABLED, 1 = ENABLED 	To indicate the status of this sensor zone;
	bits 6..0	Reserved (bit 0 = LSB).
<DescriptiveName> Tss.sensorZoneOptionsStatus:text
<DataConceptType> Data Element"
::= { sensorZoneEntry 3 }

-- 3.2.5.4 Sensor Zone Sample Period Parameter

sensorZoneSamplePeriod  OBJECT-TYPE
SYNTAX   	INTEGER (0..65535)
ACCESS  	read-write
STATUS   	mandatory
DESCRIPTION	
"<Definition> Duration of the sample period in seconds for the sensor zone over which time data is collected.  Sample period durations from 0 to 3600 are available for use.  Values 3601..65535 are reserved for future use.  A sampling period of zero (0) means that data is not being collected, while the sensor zone may continue to be enabled.
<DescriptiveName> Tss.sensorZoneSamplePeriod:quantity
<DataConceptType> Data Element
<Unit> second"
DEFVAL { 0 }
::= { sensorZoneEntry 4 }

-- 3.2.5.5 Sensor Zone Label Parameter

sensorZoneLabel  OBJECT-TYPE
SYNTAX		OCTET STRING (SIZE(0..255))
ACCESS		read-write
STATUS		optional
DESCRIPTION	
"<Definition> A text string used to describe the TSS sensor zone. A maximum string length of less than 255 may be supported.
<DescriptiveName> Tss.sensorZoneLabel:text
<DataConceptType> Data Element"
::={ sensorZoneEntry 5 }

-- 3.2.5.6 Sensor Zone Boolean AND Operator Parameter

sensorZoneAndOperator OBJECT-TYPE
SYNTAX		OCTET STRING (SIZE(8))
ACCESS		read-write
STATUS		optional
DESCRIPTION
"<Definition> This data element identifies up to eight (8) unique zones that can be sequentially combined with a Boolean AND command to provide an input to this zone, as follows:    
	Byte 1	Sensor zone number for the first Boolean AND combined with this zone,
	Byte 2	Sensor zone number for the second Boolean AND combined with this zone,
	Byte 3	Sensor zone number for the third Boolean AND combined with this zone,
	Byte 4	Sensor zone number for the fourth Boolean AND combined with this zone,
	Byte 5	Sensor zone number for the fifth Boolean AND combined with this zone,
	Byte 6	Sensor zone number for the sixth Boolean AND combined with this zone,
	Byte 7	Sensor zone number for the seventh Boolean AND combined with this zone,
	Byte 8	Sensor zone number for the eighth Boolean AND combined with this zone.
Boolean AND combinations are processed before Boolean OR combinations.  When read, this object returns last value written.
<DescriptiveName> TSS.orOperator:text
<DataConceptType> Data Element"
::= { sensorZoneEntry 6 }

-- 3.2.5.7 Sensor Zone Boolean OR Operator Parameter

sensorZoneOrOperator OBJECT-TYPE
SYNTAX		OCTET STRING (SIZE(8))
ACCESS		read-write
STATUS		optional
DESCRIPTION
"<Definition> This data element identifies up to eight (8) unique zones that can be sequentially combined with a Boolean OR command to provide an input to this zone, as follows:
	Byte 1	Sensor zone number for the first Boolean OR combined with this zone,
	Byte 2	Sensor zone number for the second Boolean OR combined with this zone,
	Byte 3	Sensor zone number for the third Boolean OR combined with this zone,
	Byte 4	Sensor zone number for the fourth Boolean OR combined with this zone,
	Byte 5	Sensor zone number for the fifth Boolean OR combined with this zone,
	Byte 6	Sensor zone number for the sixth Boolean OR combined with this zone,
	Byte 7	Sensor zone number for the seventh Boolean OR combined with this zone,
	Byte 8	Sensor zone number for the eighth Boolean OR combined with this zone.
Boolean AND combinations are processed before Boolean OR combinations.  When read, this object returns last value written.
<DescriptiveName> TSS.orOperator:text
<DataConceptType> Data Element"
::= { sensorZoneEntry 7 }

-- 3.2.6 Clock Available Parameter

clockAvailable OBJECT-TYPE
SYNTAX   	INTEGER {	clockYes (1),
       				clockNo (2) }
ACCESS  	read-only
STATUS   	mandatory
DESCRIPTION	
"<Definition> This data element identifies the availability of a real time clock within the TSS device so that time can be referenced to CTime.  
clockYes:   A real-time clock is provided within the TSS device, conformant with NTCIP 1201, and time is referenced to actual local time within the device.  
clockNo:   A real-time clock is not provided within the TSS device and time is expressed in the number of seconds since most recent device initialization.
<DescriptiveName> Tss.clockAvailable:code
<DataConceptType> Data Element"
::= { tssSystemSetup 6 }


-- 3.3 TSS CONTROL DATA ELEMENTS

tssControl  OBJECT IDENTIFIER ::= { tss 2 }
--  node for output control data elements
--  a sensor zone can be mapped to any available output
--  outputs identify discrete activity states sensed within a zone
--  output status should be refreshed upon change of state for each output

-- 3.3.1 Maximum Number of Outputs Parameter

maxOutputNumber  OBJECT-TYPE
SYNTAX   	INTEGER (1..255)
ACCESS  	read-only
STATUS   	mandatory
DESCRIPTION	
"<Definition> The maximum number of outputs supported by the TSS device.
<DescriptiveName> Tss.maxOutputNumber:quantity
<DataConceptType> Data Element
<Unit> output"
::= { tssControl 1 }

-- 3.3.2 Output Configuration Table

outputConfigurationTable  OBJECT-TYPE
SYNTAX		SEQUENCE OF OutputConfigurationEntry
ACCESS  	not-accessible
STATUS   	mandatory
DESCRIPTION	
"<Description> Table containing configuration data elements for each TSS physical device output.  The number of rows in this table is equal to the maxOutputNumber data element.  Table rows are set by the manufacturer, and row creation/deletion is not supported.
DescriptiveName> Tss.outputConfigurationTable
DataConceptType> Entity Type
<TableType> static"
::={ tssControl 2 }

outputConfigurationEntry  OBJECT-TYPE
SYNTAX		OutputConfigurationEntry
ACCESS		not-accessible
STATUS		mandatory
DESCRIPTION	
"<Definition> Row containing output configuration data elements.
<DescriptiveName> Tss.outputConfigurationEntry
<DataConceptType> Entity Type"
INDEX { outputNumber }
::={ outputConfigurationTable 1}

OutputConfigurationEntry ::= SEQUENCE {
        outputNumber			INTEGER,
	outputSensorZoneNumber		INTEGER,
        outputFailsafeMode		INTEGER,
	outputModeStatus		OCTET STRING,
	outputLabel			OCTET STRING
       }

-- 3.3.2.1 Output Number Parameter

outputNumber  OBJECT-TYPE
SYNTAX		INTEGER (1..255)
ACCESS		read-only
STATUS		mandatory
DESCRIPTION	
"<Definition>The numerical label or number assigned to a physical device output.  Output number is also the row to which the outputConfigurationTable is referenced.
<DescriptiveName> Tss.outputNumber:identifier
<DataConceptType> Data Element"
::={ outputConfigurationEntry 1}

-- 3.3.2.2 Output Sensor Zone Number Parameter

outputSensorZoneNumber  OBJECT-TYPE
SYNTAX	INTEGER (0..255)
ACCESS	read-write
STATUS	mandatory
DESCRIPTION	
"<Definition>The numerical label or number representing the sensor zone number that is associated with this output.  A value of zero (0) indicated that no sensor zone number is associated with this output.  When read, this data element returns the last value written.
<DescriptiveName> Tss.outputNumber:identifier
<DataConceptType> Data Element"
::={ outputConfigurationEntry 2}

-- 3.3.2.3 Output Failsafe Mode Parameter

outputFailsafeMode  OBJECT-TYPE
SYNTAX   	INTEGER {	failsafeModeOn (1),
       				failsafeModeOff (2),
       				overrideCommandOn (3),
       				overrideCommandOff (4),
       				normal (5) }
ACCESS  	read-write
STATUS   	mandatory
DESCRIPTION 
"<Definition> Data element that allows configuration of outputs for failure override modes, as follows:
	failsafeModeOn:   Failsafe Mode ON, the output assumes an ON state whenever there is a failure that affects the proper performance of this output;
	failsafeModeOff:   Failsafe Mode OFF, the output assumes an OFF state whenever there is a failure that affects the proper performance of this output;
	overrideCommandOn:   Override Command ON, overrides the normal operational state of the output by setting the output to ON;
	overrideCommandOff:   Override Command OFF, overrides the normal operational state of the output by setting the output to OFF;
	normal:  Normal, ends the override of the output and returns that output to normal operations.
When read, this data element returns the last value written except for the value of 5.  After a value of 5 is written, the value prior to the normal command is returned.
<DescriptiveName> Tss.outputFailsafeMode:code
<DataConceptType> Data Element"
::= { outputConfigurationEntry 3 } 

-- 3.3.2.4 Output Mode Status Parameter

outputModeStatus  OBJECT-TYPE
SYNTAX   	  OCTET STRING (SIZE(1))
ACCESS  	  read-only
STATUS   	  mandatory
DESCRIPTION 
"<Definition> A bit-mapped value as defined below for reading the status of failure override modes, as follows:
	bit 7	0 = OFF, 1 = ON 	For Failsafe Mode Status ON indicates the status of the Failsafe Mode is ON, meaning that the output assumes an ON state whenever there is a failure that in any way affects the proper performance of this output and Failsafe Mode Status OFF indicates the status of the Failsafe Mode is OFF, meaning that the output assumes an OFF state whenever there is a failure that in any way affects the proper performance of this output (MSB);
	bit 6	0 = OFF, 1 = ON	For Override Command Status ON indicates the presence of an Override to the normal operational state of the output to ON and Override Command Status Off indicates the presence of an Override to the normal operational state of the output to OFF;
	bits 5..0		Reserved (bit 0 = LSB).
<DescriptiveName> Tss.outputModeStatus:text
<DataConceptType> Data Element"
::= { outputConfigurationEntry 4 } 

-- 3.3.2.5 Output Label Parameter

outputLabel  	OBJECT-TYPE
SYNTAX		OCTET STRING (SIZE (0..255))
ACCESS		read-write
STATUS		optional
DESCRIPTION	
"<Definition> Text string to describe the TSS output.  A maximum string length of less than 255 may be supported.
<DescriptiveName> Tss.outputLabel:text
<DataConceptType> Data Element"
::={ outputConfigurationEntry 5 }

-- 3.3.3 Maximum Number of Output Groups Parameter

maxOutputGroups  OBJECT-TYPE
SYNTAX   	 INTEGER (1..32)
ACCESS  	 read-only
STATUS   	 mandatory
DESCRIPTION	
"<Definition> The number of output groups each consisting of eight (8) outputs.  Each output group represents a multiple of eight (8) sequentially numbered outputs.  Example: Output Group 1 consists of Outputs 1 to 8, Output Group 2 consists of Outputs 9 to16, etc.  A value of zero (0) means that no output groups are supported.
<DescriptiveName> Tss.maxOutputGroups:quantity
<DataConceptType> Data Element"
::= { tssControl 3 }

-- 3.3.4 Output Group Table

outputGroupTable  OBJECT-TYPE
SYNTAX   	  SEQUENCE OF OutputGroupEntry
ACCESS  	  not-accessible
STATUS   	  mandatory
DESCRIPTION	
"<Definition> A table containing input and output states for groups of eight outputs.  Each output group represents a multiple of eight (8) sequentially numbered outputs.  Output Group 1 consists of Outputs 1 to 8, Output Group 2 consists of Outputs 9 to16, etc.  The number of rows in this table is equal to the maxOutputGroups data element.  Table rows are set by the manufacturer, and row creation/deletion is not supported.
<DescriptiveName> Tss.outputGroupTable
<DataConceptType> Entity Type
<TableType> static"
::= { tssControl 4 }

outputGroupEntry  OBJECT-TYPE
SYNTAX   	  OutputGroupEntry
ACCESS  	  not-accessible
STATUS   	  mandatory
DESCRIPTION	
"<Definition> Table for output states, in groups of eight outputs.  Each output group represents a multiple of eight (8) sequentially numbered outputs.  Example: Output Group 1 consists of Outputs 1 to 8, Output Group 2 consists of Outputs 9 to16, etc.
<DescriptiveName> Tss.outputGroupEntry
<DataConceptType> Entity Type"
INDEX { outputGroupNumber }
::= { outputGroupTable 1 }

OutputGroupEntry ::= SEQUENCE {
     	outputGroupNumber		INTEGER,
	outputGroupOutputState		OCTET STRING
       }

-- 3.3.4.1 Output Group Number Parameter

outputGroupNumber  OBJECT-TYPE
SYNTAX   	INTEGER (1..32)
ACCESS  	read-only  
STATUS   	mandatory
DESCRIPTION	
"<Definition> Number of the output group, in groups of eight outputs.  Each output group represents a multiple of eight (8) sequentially numbered outputs.  Output Group 1 consists of Outputs 1 to 8, Output Group 2 consists of Outputs 9 to16, etc.  A value of zero (0) means that no output groups are supported.
<DescriptiveName> Tss.outputGroupNumber:identifier
<DataConceptType> Data Element"
::= { outputGroupEntry 1 }

-- 3.3.4.2 Output Group Output State Parameter

outputGroupOutputState  OBJECT-TYPE
SYNTAX   	OCTET STRING (SIZE(1))
ACCESS  	read-only
STATUS   	mandatory
DESCRIPTION	
"<Definition> Each bit represents the output state for each output within each output group.  Each output group represents a multiple of eight (8) sequentially numbered outputs.  Example: Output Group 1 consists of Outputs 1 to 8, Output Group 2 consists of Outputs 9 to16, etc.  An Octet String with size zero (0) means that no output groups are supported.  For Octet Strings 1..32, a value of 0 means OFF (activity not sensed) and a value of 1 means ON (activity sensed).  Bit 0 represents output 1, bit 1 represents output 2, etc., as follows:
	bit 7	0 = OFF, 1 = ON 		For output 8 within the group (MSB),
	bit 6	0 = OFF, 1 = ON 		For output 7 within the group,
	bit 5	0 = OFF, 1 = ON 		For output 6 within the group,
	bit 4	0 = OFF, 1 = ON 		For output 5 within the group,
	bit 3	0 = OFF, 1 = ON 		For output 4 within the group,
	bit 2	0 = OFF, 1 = ON 		For output 3 within the group,
	bit 1	0 = OFF, 1 = ON 		For output 2 within the group,
	bit 0	0 = OFF, 1 = ON 		For output 1 within the group  (LSB).
<DescriptiveName> Tss.outputGroupOutputState:text
<DataConceptType> Data Element"
::= { outputGroupEntry 2 }


-- 3.4 TSS DATA COLLECTION DATA ELEMENTS

tssDataCollection OBJECT IDENTIFIER ::= { tss 3 }
-- node for data collection elements

-- 3.4.1 Data Collection Table

dataCollectionTable OBJECT-TYPE
SYNTAX   	SEQUENCE OF DataCollectionEntry
ACCESS  	not-accessible
STATUS   	mandatory
DESCRIPTION 
"<Definition> Table containing the most recently completed sample period data.  The number of rows in this table is equal to the maxSensorZones data element.  Table rows are set by the manufacturer, and row creation/deletion is not supported.
<DescriptiveName> Tss.dataCollectionTable
<DataConceptType> Entity Type
<TableType> static"
::= { tssDataCollection 1 }

dataCollectionEntry OBJECT-TYPE
SYNTAX   	DataCollectionEntry
ACCESS  	not-accessible
STATUS   	mandatory
DESCRIPTION	
"<Definition> Table for data collection parameters.
<DescriptiveName> Tss.dataCollectionEntry
<DataConceptType> Entity Type"
INDEX   { sensorZoneNumber }
::= { dataCollectionTable 1 }

DataCollectionEntry ::= SEQUENCE {
--	sensorZoneNumber	INTEGER,	
        endTime			Counter,
	volumeData		INTEGER,
	percentOccupancy	INTEGER,
	speedData		INTEGER,
        zoneStatus		INTEGER
       }

-- 3.4.1.1 End Time Parameter

endTime 	OBJECT-TYPE
SYNTAX   	Counter
ACCESS  	read-write
STATUS   	mandatory
DESCRIPTION	
"<Definition> Indicates the time at which the data collection period ended for the data contained in this row, the most recently completed sample period.  If the clockAvailable data element indicates the presence of a clock, this time shall be expressed in local time as expressed in the controller-localTime data element (see NTCIP 1201); otherwise, this time shall be expressed in the number of seconds since the most recent device initialization.
<DescriptiveName> Tss.endTime:quantity
<DataConceptType> Data Element
<Unit> second"
::= { dataCollectionEntry 1 }

-- 3.4.1.2 Volume Data Parameter

volumeData 	OBJECT-TYPE
SYNTAX   	INTEGER (0..65535)
ACCESS  	read-only
STATUS   	mandatory
DESCRIPTION	
"<Definition> Counts per sample period, for the most recently completed sample period.  Counts are expressed as an integer value in the volumeData data element.  The value of 65535 shall be returned to represent a missing value.  A missing value is reported when the zoneStatus is anything other than OK for the entire sampling period.
<DescriptiveName> Tss.volumeData:quantity
<DataConceptType> Data Element
<Unit> count"
::= { dataCollectionEntry 2 }

-- 3.4.1.3 Percent Occupancy Parameter

percentOccupancy OBJECT-TYPE
SYNTAX   	 INTEGER (0..1000 | 65535)
ACCESS  	 read-only
STATUS   	 mandatory
DESCRIPTION	
"<Definition> Percent occupancy over the sample period for the most recently completed sample period. Occupancy is expressed in tenths of a percent, from 0 to 100.0 percent, in the percentOccupancy data element.  The value of 65535 shall be return to represent an invalid or missing value.  A missing value is reported when the zoneStatus is anything other than OK for the entire sampling period.  Values 1001 through 65534 are reserved for future use.
<DescriptiveName> Tss.percentOccupancy:percent
<DataConceptType> Data Element
<Unit> percent"
::= { dataCollectionEntry 3 }

-- 3.4.1.4 Speed Data Parameter

speedData 	OBJECT-TYPE
SYNTAX   	INTEGER (0..2550 | 65535)
ACCESS  	read-only
STATUS   	mandatory
DESCRIPTION	
"<Definition> Arithmetic mean of speeds collected over the sample period with units of 1/10ths of km/h, for the most recently completed sample period. For a volume of zero during the sample period, the value of 65535 shall be returned to represent an invalid or missing value.  A missing value is reported when the zoneStatus is anything other than OK for the entire sampling period.  Values 2551 through 65534 are reserved for future use.
<DescriptiveName> Tss.speedData:rate
<DataConceptType> Data Element
<Unit> tenths of km/h"
::= { dataCollectionEntry 4 }

-- 3.4.1.5 Zone Status Parameter

zoneStatus  OBJECT-TYPE
SYNTAX   INTEGER {	other (1),
       			oK (2),
			initializing (3),
       			noActivity (4),
       			maxPresence (5),
       			configurationError (6),
       			erraticCounts (7),
       			disabled (8),
       			overrideActive (9),
       			sensorFailure (10) }				
ACCESS  	read-only
STATUS   	mandatory
DESCRIPTION	
"<Definition> Detailed status returned as result of diagnostics, as follows:
       Value		Meaning
	other:   Status returned indicating an error has occurred within the device for which there is no defined definition within this data element,
	oK:   Status returned indicating OK,
	initializing:   Status returned indicating an initialization or diagnostics procedure is in progress,
	noActivity:   Status returned indicating no activity error condition,
	maxPresence:   Status returned indicating max presence error condition,
	configurationError:   Status returned indicating an error within the device configuration setup,
	erraticCounts:   Status returned indicating erratic counts,
	disabled:   Status returned indicating that the zone is disabled.
	overrideActive:   Status returned indicating an override is active.
	sensorFailure:   Status returned indicating a sensing element failure,
If a condition occurs during the sample period, then that state remains for the duration of that sample period.  If multiple conditions occur during a sample period, the last reported condition, other than OK, is retained.
<DescriptiveName> Tss.zoneStatus:code
<DataConceptType> Data Element"
::= { dataCollectionEntry 5 }

-- 3.4.2 Data Buffer Table

dataBufferTable OBJECT-TYPE
SYNTAX   	SEQUENCE OF DataBufferEntry
ACCESS  	not-accessible
STATUS   	mandatory
DESCRIPTION	
"<Definition> Table containing the second most recently completed previous sample period data, which value is specified by the value of the sensorZoneSamplePeriod data element.  The previous period data overwrites the data for the sample period data immediately preceding the previous sample period. The number of rows in this table is equal to the maxSensorZones data element.  Table rows are set by the manufacturer, and row creation/deletion is not supported.
<DescriptiveName> Tss.dataBufferTable
<DataConceptType> Entity Type
<TableType> static"
::= { tssDataCollection 2 }

dataBufferEntry OBJECT-TYPE
SYNTAX   	DataBufferEntry
ACCESS  	not-accessible
STATUS   	mandatory
DESCRIPTION	
"<Definition> Table containing the data collection parameters for the second most recently completed previous sample period.
<DescriptiveName> Tss.dataBufferEntry
<DataConceptType> Entity Type"
INDEX   { sensorZoneNumber }
::= { dataBufferTable 1 }

DataBufferEntry ::= SEQUENCE {
--        sensorZoneNumber                INTEGER,
	endTimeBuffer			Counter,
       	volumeDataBuffer		INTEGER,
	percentOccupancyBuffer		INTEGER,
	speedDataBuffer			INTEGER,
       	zoneStatusBuffer		INTEGER
       }

-- 3.4.2.1 End Time Buffer Parameter

endTimeBuffer 	OBJECT-TYPE
SYNTAX   	Counter
ACCESS  	read-only
STATUS   	mandatory
DESCRIPTION	
"<Definition> Indicates the time at which the data collection period ended for the data contained in this row, the second most recently completed previous sample period.  If the clockAvailable data element indicates the presence of a clock, this time shall be expressed in local time as expressed in the controller-localTime data element (see NTCIP 1201); otherwise, this time shall be expressed in the number of seconds since the most recent device initialization.
<DescriptiveName> Tss.endTimeBuffer:quantity
<DataConceptType> Data Element
<Unit> second"
::= { dataBufferEntry 1 }

-- 3.4.2.2 Volume Data Buffer Parameter

volumeDataBuffer OBJECT-TYPE
SYNTAX   	 INTEGER (0..65535)
ACCESS  	 read-only
STATUS   	 mandatory
DESCRIPTION	
"<Definition> Counts per sample period, for the second most recently completed previous sample period.  Counts are expressed as an integer value in the volumeData data element.  The value of 65535 shall be returned to represent a missing value.  A missing value is reported when the zoneStatusBuffer is anything other than OK for the entire sampling period.
<DescriptiveName> Tss.volumeDataBuffer:quantity
<DataConceptType> Data Element
<Unit> count"
::= { dataBufferEntry 2 }

-- 3.4.2.3 Percent Occupancy Buffer Parameter

percentOccupancyBuffer OBJECT-TYPE
SYNTAX   	INTEGER (0..1000 | 65535)
ACCESS  	read-only
STATUS   	mandatory
DESCRIPTION	
"<Definition> Percent occupancy over the sample period for the second most recently completed previous sample period.  Occupancy is expressed in tenths of a percent, from 0 to 100.0 percent, in the percentOccupancy data element.  The value of 65535 shall be returned to represent an invalid or missing value.  A missing value is reported when the zoneStatusBuffer is anything other than OK for the entire sampling period.  Values 1001 through 65534 are reserved for future use.
<DescriptiveName> Tss.percentOccupancyBuffer
<DataConceptType> Data Element
<Unit> percent"
::= { dataBufferEntry 3 }

-- 3.4.2.4 Speed Data Buffer Parameter

speedDataBuffer OBJECT-TYPE
SYNTAX   	INTEGER (0..2550 | 65535)
ACCESS  	read-only
STATUS   	mandatory
DESCRIPTION	
"<Description> Arithmetic mean of speeds collected over the sample period, with units of 1/10ths of km/hr, for the second most recently completed previous sample period.  For a volume of zero during the sample period, the value of 65535 shall be returned to represent an invalid or missing value.  A missing value is reported when the zoneStatusBuffer is anything other than OK for the entire sampling period.  Values 2551 through 65534 are reserved for future use.
<DescriptiveName> Tss.speedDataBuffer:rate
<DataConceptType> Data Element
<Unit> tenths of km/hr"
::= { dataBufferEntry 4 }

-- 3.4.2.5 Zone Status Buffer Parameter

zoneStatusBuffer  OBJECT-TYPE
SYNTAX   	INTEGER {	other (1),
       				oK (2),
				initializing (3),
       				noActivity (4),
       				maxPresence (5),
       				configurationError (6),
       				erraticCounts (7),
       				disabled (8),
       				overrideActive (9),
       				sensorFailure (10) }				
ACCESS  	read-only
STATUS   	mandatory
DESCRIPTION	"Detailed status returned as result of diagnostics, for the previous sample period, as follows:
       Value		Meaning
	other:   Status returned indicating an error has occurred within the device for which there is no defined definition within this data element,
	oK:   Status returned indicating OK,
	initializing:   Status returned indicating an initialization or diagnostics procedure is in progress,
	noActivity:   Status returned indicating no activity error condition,
	maxPresence:   Status returned indicating max presence error condition,
	configurationError:   Status returned indicating an error within the device configuration setup,
	erraticCounts:   Status returned indicating erratic counts,
	disabled:   Status returned indicating that the zone is disabled,
	overrideActive:   Status returned indicating an override is active,
	sensorFailure:   Status returned indicating a sensing element failure.
If a condition occurs during the sample period, then that state remains for the duration of that sample period.
<DescriptiveName> Tss.zoneStatusBuffer:code
<DataConceptType> Data Element"
::= { dataBufferEntry 5 }

-- 3.5 TSS INDUCTIVE LOOP DETECTOR DATA ELEMENTS
tssInductiveLoop OBJECT IDENTIFIER ::= { tss 4 }

-- This node contains the configuration objects specific to inductive loop detectors
-- These objects setup physical parameters on the detector that are controlled on a per output basis. 
-- These objects are only valid for the zones that map directly to an output on the detector. 
-- Zone 1 maps to output 1 and Zone 2 maps to output 2 on a two output detector and Zone 3 maps 
--  to output 3, and Zone 4 maps to output 4 on a four output detector.
--  For inductive loop detectors, the term "channel" is often used to refer to an "output".

-- 3.5.1 Loop System Setup Table

loopSensorSetupTable OBJECT-TYPE
SYNTAX	SEQUENCE OF LoopSensorSetupEntry
ACCESS 	not-accessible
STATUS 	mandatory
DESCRIPTION 
"<Definition> This table contains inductive loop detector sensor zone parameters.  The number of rows in this table does not exceed maxSensorZones.  This table contains the configuration objects specific to inductive loop detectors.  These objects set up physical parameters on the detector that are controlled on a per output basis.  A zone maps directly to an output on an inductive loop detector - Zone 1 maps to output 1, Zone 2 maps to output 2, and, on a four output inductive loop detector, Zone 3 maps to output 3 and Zone 4 maps to output 4.  Table rows are set by the manufacturer, and row creation/deletion is not supported.
<DescriptiveName> Tss.loopSensorSetupTable
<DataConceptType> Entity Type
<TableType> static"
::= { tssInductiveLoop 1 }

loopSensorSetupEntry OBJECT-TYPE
SYNTAX	LoopSensorSetupEntry
ACCESS 	not-accessible
STATUS 	mandatory
DESCRIPTION 
"<Definition> Row in table that contains inductive loop detector sensor zone parameters.  The number of rows in this table does not exceed maxSensorZones or maxOutputNumber, whichever is greater.  Table rows are set by the manufacturer, and row creation/deletion is not supported.
<DescriptiveName> Tss.loopSensorSetupEntry
<DataConceptType> Entity Type"
INDEX { sensorZoneNumber }
::= { loopSensorSetupTable 1 }

LoopSensorSetupEntry ::= SEQUENCE {
--	sensorZoneNumber		INTEGER,
	zoneSensitivityMode		INTEGER,
       	zoneSensitivity			OCTET STRING,
       	zoneFrequencyRange		OCTET STRING
       }

-- 3.5.1.1 Zone Sensitivity Mode

zoneSensitivityMode 	OBJECT-TYPE
SYNTAX 			INTEGER {	deltaL (1),
					deltaLOverSqrtL (2),
					deltaLOverL (3) }
ACCESS 	read-only
STATUS 	mandatory
DESCRIPTION	
"<Definition> Sensitivity mode in use (3=[delta]L/L, 2=[delta]L/[squareroot]L, 1=[delta]L).  This is a characteristic of the loop detector being used.
<DescriptiveName> Tss.zoneSensitivityMode:code
<DataConceptType> Data Element"
::= { loopSensorSetupEntry 1 }

-- 3.5.1.2 Zone Sensitivity

zoneSensitivity  OBJECT-TYPE
SYNTAX 	OCTET STRING (SIZE(2))
ACCESS 	read-write
STATUS 	mandatory
DESCRIPTION	
"<Definition> This bit-mapped object allows the setting and reading of the sensitivity for the zone as follows:
bit 3,bit 2,bit1,bit 0		Meaning
	0000		Zone OFF (Disabled) (LSB)
	0001		Detect [delta]L = 512 nanohenries or [delta]L/L = 0.64%
	0010		Detect [delta]L = 256 nanohenries or [delta]L/L = 0.32%
	0011		Detect [delta]L = 128 nanohenries or [delta]L/L = 0.16%
	0100		Detect [delta]L = 64 nanohenries or [delta]L/L = 0.08%
	0101		Detect [delta]L = 32 nanohenries or [delta]L/L = 0.04%
	0110		Detect [delta]L = 16 nanohenries or [delta]L/L = 0.02%
	0111		Detect [delta]L = 8 nanohenries or [delta]L/L = 0.01%
	or, if bit 15=1	Detect [delta]L = 0 to 32,767 nanohenries or [delta]L/L = 0 to 32.767% (MSB)
These sensitivity definitions are equal with a loop inductance of 80 microhenries.  A detector need not support all of these settings.  However, the sensitivities it does support must conform with these definitions, e.g. a sensitivity setting of 3 is always 128 nanohenries or 0.16% with an 80 microhenry loop.  If bit 15=1, bit 0 – bit 14 contain the sensitivity in nanohenries or one-thousands of a percent, e.g. 3650 is 3.650%.  A value of 65535 shall be returned to represent invalid data or not a physical zone.  Values of 8 through 32767 are reserved.
<DescriptiveName> Tss.zoneSensitivity:text
<DataConceptType> Data Element"
::={ loopSensorSetupEntry 2 }

-- 3.5.1.3 Zone Frequency Mode

zoneFrequencyRange	OBJECT-TYPE
SYNTAX 	OCTET STRING (SIZE(1))
ACCESS 	read-write
STATUS 	mandatory
DESCRIPTION  
"<Definition> Allows the setting and reading of the frequency range as follows:
       bit 2, bit 1, bit 0 		Meaning	
       	000 			Frequency Range 0 (lowest frequency) (LSB)
       	001 			Frequency Range 1
       	010 			Frequency Range 2
	011 			Frequency Range 3 (highest frequency for 4 freq. unit) (MSB)
As the frequency number increases the operation frequency shall increase.  The loop frequency at the lowest frequency setting shall be less than 88% of the loop frequency at the highest frequency setting.   A value of 255 shall be returned to represent invalid data or not a physical zone.  Values of 8 through 254 are reserved.
<DescriptiveName>Tss.zoneFrequencyRange:text
<DataConceptType> Data Element"
::= { loopSensorSetupEntry 3 }

-- 3.5.2 Loop Output Conditioning Table

loopOutputConditioningTable OBJECT-TYPE
SYNTAX	SEQUENCE OF LoopOutputConditioningEntry
ACCESS 	not-accessible
STATUS 	mandatory
DESCRIPTION 
"<Definition> Each table row contains objects for configuring inductive loop detector sensor zone outputs.  The number of rows in this table does not exceed maxSensorZones.  Table rows are set by the manufacturer, and row creation/deletion is not supported.
<DescriptiveName> Tss.loopOutputConditioningTable
<DataConceptType> Entity Type
<TableType> static"
::= { tssInductiveLoop 2 }

loopOutputConditioningEntry OBJECT-TYPE
SYNTAX 	LoopOutputConditioningEntry
ACCESS 	not-accessible
STATUS 	mandatory
DESCRIPTION 
"<Definition> Each table row contains inductive loop detector sensor zone output conditioning parameters.
<DescriptiveName> Tss.loopOutputConditioningEntry
<DataConceptType> Entity Type"
INDEX { sensorZoneNumber }
::= { loopOutputConditioningTable 1 }

LoopOutputConditioningEntry ::= SEQUENCE {
--        sensorZoneNumber        INTEGER,
	zoneOutputMode		INTEGER,
	zoneMaxPresenceTime	INTEGER,
	zoneOutputDelayTime	INTEGER,
	zoneOutputExtendTime	INTEGER,
	zoneOutputExtendEnable	OCTET STRING,
	zoneOutputDelayEnable	OCTET STRING 
}

-- 3.5.2.1 Zone Output Mode

zoneOutputMode	OBJECT-TYPE
SYNTAX 		INTEGER {	other (1),
       				pulse (2),
				presence (3) }
ACCESS 	read-write
STATUS 	mandatory
DESCRIPTION 
"<Definition> This object sets the length of the output during a detect condition.  These detect outputs are described as follows:
	other:   Other – an output mode other than that defined in this standard
	pulse:   Pulse - a pulse of 125ms (+/-25ms) is output when a vehicle is detected.
	presence:   Presence - the output lasts the duration of a detect condition or until the detector tunes out the detect signal.
A value of 255 shall be returned to represent invalid data.
<DescriptiveName> Tss.zoneOutputMode:code
<DataConceptType> Data Element"
::= { loopOutputConditioningEntry 1 }

-- 3.5.2.2 Zone Max Presence Feature Time

zoneMaxPresenceTime	OBJECT-TYPE
SYNTAX 			INTEGER (0..65535)
ACCESS 			read-write
STATUS 			optional
DESCRIPTION	
"<Definition> This object sets the maximum time that the zone will hold presence before retuning.  Values of 1 to 65534 seconds are available.  A value of 0 disables this timer and prevents a sensor zone occupancy from being tuned out at the end of a specific time.  A value of 65,535 represents invalid data.
<DescriptiveName> Tss.zoneMaxPresenceTime:quantity
<DataConceptType> Data Element
<Unit> second"
::= { loopOutputConditioningEntry 2 }

-- 3.5.2.3 Zone Output Delay Time

zoneOutputDelayTime	OBJECT-TYPE
SYNTAX 			INTEGER (0..65535)
ACCESS 			read-write
STATUS 			optional
DESCRIPTION	
"<Definition> The output for the zone is delayed from start of sensor zone occupancy by the time specified (tenths of a second:  00.0 to 6553.5 sec).  For the output to actually switch, the sensor zone occupancy must be continuous and still be present at the end of the delay time.
<DescriptiveName> Tss.zoneOutputDelayTime:quantity
<DataConceptType> Data Element
<Unit> tenths of a second
REFERENCE
NEMA TS2 Clause 3.5.5.5.4.c and 6.5.2.24.1"  
::= { loopOutputConditioningEntry 3 }

-- 3.5.2.4 Zone Output Extend Time

zoneOutputExtendTime	OBJECT-TYPE
SYNTAX 			INTEGER (0..65535)
ACCESS			read-write
STATUS 			optional
DESCRIPTION	
"<Definition> The output for the zone is extended, after the end of the period in which the sensor zone is occupied, by the amount of time specified (tenths of a second: 00.0 to 6553.5 sec).
<DescriptiveName> Tss.zoneOutputExtendTime:quantity
<DataConceptTime> Data Element
<Unit> tenths of a second
REFERENCE
NEMA TS2 Clause 3.5.5.5.4.d and 6.5.2.24.2"  
::= { loopOutputConditioningEntry 4 }

-- 3.5.2.5 Zone Output Extend Enable

zoneOutputExtendEnable	OBJECT-TYPE
SYNTAX 			OCTET STRING (SIZE(1))
ACCESS 			read-write
STATUS 			optional
DESCRIPTION  
"<Definition> A bit-mapped value as defined below to enable and disable the extend time for the sensor zone output, as follows:
	bit 7	0 = NO, 1 = YES	HIGH on output 1 arming pin to enable extend time for the zone (MSB),
	bit 6	0 = NO, 1 = YES	HIGH on output 2 arming pin to enable extend time for the zone,
	bit 5	0 = NO, 1 = YES	HIGH on output 3 arming pin to enable extend time for the zone,
	bit 4	0 = NO, 1 = YES	HIGH on output 4 arming pin to enable extend time for the zone,
	bit 3	0 = NO, 1 = YES	LOW on output 1 arming pin to enable extend time for the zone (MSB),
	bit 2	0 = NO, 1 = YES	LOW on output 2 arming pin to enable extend time for the zone,
	bit 1	0 = NO, 1 = YES	LOW on output 3 arming pin to enable extend time for the zone,
	bit 0	0 = NO, 1 = YES	LOW on output 4 arming pin to enable extend time for the zone (LSB).
Extend time is always enabled for the zone if all bits are zero (0).
<DescriptiveName> Tss.zoneOutputExtendEnable:text
<DataConceptType> Data Element
REFERENCE
NEMA TS2 Clause 6.5.2.8.7, 6.5.2.24 and 6.5.2.25.6"
::= { loopOutputConditioningEntry 5 }

-- 3.5.2.6 Zone Output Delay Enable

zoneOutputDelayEnable	OBJECT-TYPE
SYNTAX 	OCTET STRING (SIZE(1))
ACCESS 	read-write
STATUS 	optional
DESCRIPTION  
"<Definition> A bit-mapped value as defined below to enable and disable the delay time for the sensor zone output, as follows:
	bit 7	0 = NO, 1 = YES	HIGH on output 1 arming pin to enable delay time for the zone (MSB),
	bit 6	0 = NO, 1 = YES	HIGH on output 2 arming pin to enable delay time for the zone,
	bit 5	0 = NO, 1 = YES	HIGH on output 3 arming pin to enable delay time for the zone,
	bit 4	0 = NO, 1 = YES	HIGH on output 4 arming pin to enable delay time for the zone,
	bit 3	0 = NO, 1 = YES	LOW on output 1 arming pin to enable delay time for the zone (MSB),
	bit 2	0 = NO, 1 = YES	LOW on output 2 arming pin to enable delay time for the zone,
	bit 1	0 = NO, 1 = YES	LOW on output 3 arming pin to enable delay time for the zone,
	bit 0	0 = NO, 1 = YES	LOW on output 4 arming pin to enable delay time for the zone,
Delay time is always enabled for the zone if all bits are zero (0).
<DescriptiveName> Tss.zoneOutputDelayEnable:text
<DataConceptType> Data Element
REFERENCE
NEMA TS2 Clause 6.5.2.8.7, 6.5.2.24 and 6.5.2.25.6"
::= { loopOutputConditioningEntry 6 }

-- 3.5.3 Loop System Status Table

loopSystemStatusTable 	OBJECT-TYPE
SYNTAX			SEQUENCE OF LoopSystemStatusEntry
ACCESS 			not-accessible
STATUS 			mandatory
DESCRIPTION 
"<Definition> This table contains inductive loop detector sensor zone status parameters.  The number of rows in this table does not exceed maxSensorZones.  This table contains instantaneous zone status objects specific to inductive loop detectors.  The zoneDetectStatus object may be used by external systems for doing detailed traffic analysis.  A zone maps directly to an output on an inductive loop detector - Zones 1 maps to output 1, Zone 2 maps to output 2, and, on a four output inductive loop detector, Zone 3 maps to output 3 and Zone 4 maps to output 4.  Table rows are set by the manufacturer, and row creation/deletion is not supported.
<DescriptiveName> Tss.loopSystemStatusTable
<DataConceptType> Entity Type
<TableType> static"
::= { tssInductiveLoop 3 }

loopSystemStatusEntry 	OBJECT-TYPE
SYNTAX 			LoopSystemStatusEntry
ACCESS 			not-accessible
STATUS 			mandatory
DESCRIPTION 
"<Definition> Rows in this table contain inductive loop detector sensor zone status parameters.  The number of rows in this table does not exceed maxSensorZones.  Table rows are set by the manufacturer, and row creation/deletion is not supported.
<DescriptiveName> Tss.loopSystemStatusEntry
<DataConceptType> Entity Type"
INDEX { sensorZoneNumber }
::= { loopSystemStatusTable 1 }

LoopSystemStatusEntry ::= SEQUENCE {
-- 	sensorZoneNumber	INTEGER,
	zoneInductance		INTEGER,
	zoneFrequency		INTEGER,
	zoneInductanceChange	INTEGER,
	zoneFaultHistory	OCTET STRING,
	zoneFaultCount		INTEGER 
}

-- 3.5.3.1 Zone Inductance

zoneInductance	OBJECT-TYPE
SYNTAX 			INTEGER (0..65535)
ACCESS			read-only
STATUS 			optional
DESCRIPTION	
"<Definition> The detector unit calculates the inductance of the loop attached to the zone.  The resolution is in tenths of a microhenry.  For example, 852.4 microhenries will be represented as 8524.  Resolution does not imply accuracy, refer to manufacturers data sheet.  A value of 65535 shall be returned to represent invalid data or not a physical zone.
<DescriptiveName> Tss.zoneInductance:quantity
<DataConceptType> Data Element
<Unit> tenths of a microhenry"
::= { loopSystemStatusEntry 1 }

-- 3.5.3.2 Zone Frequency

zoneFrequency		OBJECT-TYPE
SYNTAX 			INTEGER (0..16777216)
ACCESS			read-only
STATUS 			optional
DESCRIPTION  
"<Definition> This is the frequency of the inductive loop attached to the zone.  The frequency resolution is one-tenth hertz.  For example, 53240 Hz will be represented as 532400.  Resolution does not imply accuracy, refer to manufacturers data sheet.  A value of 16777216 shall be returned to represent invalid data or not a physical zone.
<DescriptiveName> Tss.zoneFrequency:quantity
<DataConceptType> Data Element
<Unit> one-tenth hertz"
::= { loopSystemStatusEntry 2 }

-- 3.5.3.3 Zone Inductance Change 

zoneInductanceChange	OBJECT-TYPE
SYNTAX 			INTEGER (0.. 8388608)
ACCESS 			read-only
STATUS 			optional
DESCRIPTION	
"<Definition> The maximum inductance change seen since the last start of sensor zone occupancy is returned. The value is signed, and the resolution is to one nanohenry or one one-thousandth of a percent.  Resolution does not imply accuracy.  A positive value represents movement in the Call direction
<DescriptiveName> Tss.zoneInductanceChange:quantity
<DataConceptType> Data Element
<Unit> nanohenry"
::= { loopSystemStatusEntry 3 }

-- 3.5.3.4 Zone Fault History

zoneFaultHistory	OBJECT-TYPE
SYNTAX 			OCTET STRING (SIZE (1))
ACCESS 			read-only
STATUS 			mandatory
DESCRIPTION  
"<Definition> A bit-mapped value representing the history of faults in Zone since the last unit reset.
	bit 7	0 = NO, 1 = YES 	To indicate that a current fault exists on the loop connected to the zone (MSB);
	bit 6	0 = NO, 1 = YES	To indicate that the loop connected to the zone is open or this was the last fault.  (May be also be called a Maximum Presence fault by external units.);
	bit 5	0 = NO, 1 = YES	To indicate that the loop connected to the zone is shorted or this was the last fault.  (May also be called a No Activity fault by external units.);
	bit 4	0 = NO, 1 = YES	To indicate that the loop inductance of the loop connected to the zone is currently >/= +/-25% of reference or this was the last fault.  (May also be called a Erratic Count fault by external units.);
	bits 3..1		Reserved;
	bit 0	0 = NO, 1 = YES	To indicate that data for this value is invalid data or this is not a physical zone (LSB).
<DescriptiveName> Tss.loopFaultHistory:text
<DataConceptType> Data Element"
::= { loopSystemStatusEntry 4 }

-- 3.5.3.5 Zone Fault Count

zoneFaultCount		OBJECT-TYPE
SYNTAX 			INTEGER (0..255)
ACCESS 			read-only
STATUS 			mandatory
DESCRIPTION	
"<Definition> Number of faults in the zone since the last unit reset.  These faults include open circuit; short circuit and +/-25% drift faults.  The fault count may also include faults other than those defined in this standard.  The count after 255 is 255.
<DescriptiveName> Tss.zoneFaultCount:quantity
<DataConceptType> DataElement
<Unit> fault"
::= { loopSystemStatusEntry 5 }

END
