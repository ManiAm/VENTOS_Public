-- B.1	CHAP MIB Header
-- 
-- Filename:    2103v0203 CHAP.mib
-- Description: This MIB defines objects represents the data elements that 
--              support CHAP
-- Source:      NTCIP 2103 v02.03
--
-- MIB Revision History:
-- 10/14/04     Created header and MIB inside Word Document
--              
-- 
-- Copyright 2004 by the American Association of State Highway and
-- Transportation Officials (AASHTO), the Institute of Transportation 
-- Engineers (ITE), and the National Electrical Manufacturers Association 
-- (NEMA).  All intellectual property rights, including, but not limited to, 
-- the rights of reproduction in whole or in part in any form, translation 
-- into other languages and display are reserved by the copyright owners under 
-- the laws of the United States of America, the Universal Copyright 
-- Convention, the Berne Convention, and the International and Pan American 
-- Copyright Conventions.
--
--                     Joint AASHTO, ITE, and NEMW
--            NTCIP Management Information Base and Data Dictionary
--                        DISTRIBUTION NOTICE
--
-- To the extent and in the limited event these materials are distributed by
-- AASHTO/ITE/NEMA in the form of a Management Information Base ("MIB") or
-- Data Dictionary ("DD"), AASHTO/ITE/NEMA extends the following permissions:
-- 
--  (i) you may make and/or distribute unlimited copies (including derivative
-- works) of the MIB, including copies for commercial distribution, provided
-- that (a) each copy you make and/or distribute contains this Notice and (b)
-- each derivative work of the MIB uses the same module name followed by "-",
-- followed by your Internet Assigned Number Authority (IANA)-assigned
-- enterprise number;
-- (ii) use of the MIB is restricted in that the syntax field may be modified
-- but only to reflect a more restrictive sub-range or enumerated values;
-- (iii) the description field may be modified but only to the extent that:
-- (a) only those bit values or enumerated values that are supported are
-- listed; and (b) the more restrictive subrange is expressed.
-- 
-- These materials are delivered "AS IS" without any warranties as to their
-- use or performance.
-- 
-- AASHTO/ITE/NEMA AND THEIR SUPPLIERS DO NOT WARRANT THE PERFORMANCE OR
-- RESULTS YOU MAY OBTAIN BY USING THESE MATERIALS.  AASHTO/ITE/NEMA AND THEIR
-- SUPPLIERS MAKE NO WARRANTIES, EXPRESS OR IMPLIED, AS TO NONINFRINGEMENT OF
-- THIRD PARTY RIGHTS, MERCHANTABILITY, OR FITNESS FOR ANY PARTICULAR PURPOSE.
-- IN NO EVENT WILL AASHTO, ITE OR NEMA OR THEIR SUPPLIERS BE LIABLE TO YOU OR
-- ANY THIRD PARTY FOR ANY CLAIM OR FOR ANY CONSEQUENTIAL, INCIDENTAL OR
-- SPECIAL DAMAGES, INCLUDING ANY LOST PROFITS OR LOST SAVINGS, ARISING FROM
-- YOUR REPRODUCTION OR USE OF THESE MATERIALS, EVEN IF AN AASHTO, ITE, OR 
-- NEMA REPRESENTATIVE HAS BEEN ADVISED OF THE POSSIBILITY OF SUCH DAMAGES.
-- Some states or jurisdictions do not allow the exclusion or limitation of
-- incidental, consequential or special damages, or the exclusion of implied
-- warranties, so the above limitations may not apply to you.
-- 
-- Use of these materials does not constitute an endorsement or affiliation by
-- or between AASHTO, ITE, or NEMA and you, your company, or your products and
-- services.
-- 
-- NTCIP is a trademark of AASHTO/ITE/NEMA.
--******************************************************************************

CHAP-MIB1     DEFINITIONS ::= BEGIN

IMPORTS
    OBJECT-TYPE
              FROM RFC-1212
    layers
              FROM NTCIP8004-A-2004;

chap OBJECT IDENTIFIER ::= {layers 1}

-- All nodes underneath the chap node shall only be accessible by the 
-- administrator community name.

-- NOTE—These objects should only be exchanged when the connection is known to 
-- be private, i.e. the connection should either be physically secure from 
-- outside monitoring (e.g., locally connected through a direct null-modem 
-- cable) or the connection should ensure privacy through a well designed 
-- encryption scheme such as Secure Sockets Layer (SSL).  Users should be 
-- aware that dial-up connections and wireless technologies are not private 
-- unless some sort of encryption layer is used.  

-- B.2	Maximum Secrets Parameter
chapMaxSecrets   OBJECT-TYPE
   SYNTAX   INTEGER (1..255)
   ACCESS   read-only
   STATUS   mandatory
   DESCRIPTION
   "The number of rows that are listed in the Chap Secrets Table."
   ::= { chap 1 }

-- B.3	CHAP Secret Table
chapSecretTable   OBJECT-TYPE
   SYNTAX   SEQUENCE OF ChapSecretEntry
   ACCESS   not-accessible
   STATUS   mandatory
   DESCRIPTION
   "A table containing the names and secrets for the CHAP authentication 
   protocol."
   ::= { chap 2 }

chapSecretEntry OBJECT-TYPE
SYNTAX   ChapSecretEntry
ACCESS   not-accessible
STATUS   mandatory
DESCRIPTION
"This object defines an entry in the CHAP Secrets Table"
INDEX { chapName }
::= { chapSecretTable 1 }

ChapSecretEntry ::= SEQUENCE {
chapName      OCTET STRING,
chapSecret    OCTET STRING }

chapName OBJECT-TYPE
SYNTAX   OCTET STRING (SIZE (8..20))
ACCESS   read-write
STATUS   mandatory
DESCRIPTION
"The name of a peer system (or user) as it would be recorded in a CHAP 
challenge."
::= { chapSecretEntry 1 }

chapSecret   OBJECT-TYPE
SYNTAX   OCTET STRING (SIZE (16..64))
ACCESS   read-write
STATUS   mandatory
DESCRIPTION
"This object contains the secret used for the associated name when using
the CHAP authentication protocol."
::= { chapSecretEntry 2 }

END
